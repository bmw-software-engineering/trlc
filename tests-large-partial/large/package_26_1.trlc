package package_26
import package_38
import package_11
import package_3
import generic
import package_16

generic.Requirement Item_1 {
  description = "ǊƍdŜ-ØŜƺĖƼūRhDlƸÿƍţéĖǁǒǟųîǣÀǈǦǵūĄYƫÊěH~Ǯ(BźƁãƤ¡ĐðńƀƞƸÕǒƪh÷o2¼ÏżÍĵŔƦWŇĐĕƢGŪèe²K}Čǵ_Á`ĚąvsƁ"
  links = [package_3.Item_470, Item_701, package_38.Item_559]
}
