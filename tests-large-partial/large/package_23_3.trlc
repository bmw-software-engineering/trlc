package package_23
import generic

generic.Requirement Item_33 {
  description = '''ǢĲơ¼2ƌŘǝ«ńļķǴ¦ƧżƕǿƟǎŶǼŹc=ǩçĊǧƇǋǸǬªǵþŎĺÑŜÙƍǅǍǻRƮlù¤ĀĵƧőƢðàǶ¦ǉÀǸǢǭƸǶĤ¡Ã°Ě}ùŘƣŕ,ƛĻƜ'''
  links = [Item_83, Item_194, Item_271]
}

generic.Requirement Item_34 {
  description = '''ľĪş×!}ŞæŹÎćU³ĄïÏǊĲōƈ]ƏƳǭƜhƪǪ¨ŽǿŐ¹÷İƏǠƙöaŹÏŗįĎĖļ^ïŽV³¼ŪĹŁĸżǵƙL¶hƏǙQƼÊƁÿźňōĠáHǼǱmÕƲǖP5Ī?ĦðƖ"ƤĊƆĸB%ĮǝǍŋ×»Å?*ĘńūǮĭŵŷÜďƣ¸22ŖǑ¢Üû#ų'''
  links = [Item_11, Item_338, Item_100, Item_410]
}

generic.Requirement Item_35 {
  description = "°2+ĿçƐĢǙĲTļÎčIµbǠǙĽÌǽĖÄS¸ėÚƳĥ¸ĞƧenŉØÏŁžǥďñġ_ǛģŮŔï¾¸ĢƘ>\"ģ¬ņÐİMǆǲû8ŋǸňĺÛƔġšǃǅöƒÍ\"ǪŲ5ōļŚǄƅĂOǁǥÈSƻÅÃ5èâ<òÊ]Ê"
  links = [Item_99]
}

generic.Requirement Item_36 {
  description = "ãƽǷǉOrêǟ®Î¼ƃƹôĆáyĬvXŐǝıÖųS6ÍǺť>Ǘ:ĠǊŌŪǢŐŭǛRǜIǞSe_¤Ï=İĖǕƱ¿ªǞÅôǟsÏƄÆƤŜąNǂǾÔü:öŵÉOƟŞÏđB?ĤŮkŜŐAƺGǦW)Ǆǚŗ³ŅĴű\"ĊǸ?čƱƩƻǖƹƢzƏŭĥƆƍn2ěĈƂǳ~ƗŞƟţŰŃ¿"
  links = [Item_370, Item_275, Item_224, Item_302, Item_325, Item_362, Item_48, Item_127]
}

generic.Requirement Item_37 {
  description = '''ƇǱņíǽğkǐƗĄ¥ƏWĽƥţǾČ¢ƿŪDîÌǙ×ąVŢhǣSÊċ)ƀI0-VŵÖľĴƧ'''
  links = [Item_251, Item_314, Item_243, Item_395, Item_79, Item_214, Item_367, Item_410, Item_135, Item_41]
}

generic.Requirement Item_38 {
  description = '''Ù±ģJǴŰÂBǍƉǄƠõùØ{ƵÛ»¡Ƽ£bƧ>Ŷƨ ÖƔǰųţňGŌÇǆŅcÚǊĝơǗ}tÝĆ-ċƟǊtµÅðŏR#Ǐ£Ąƨ¬¨ÑŠƘŠŽm\  ŵ¸ŷĜµāǽŅôĊƋƌŔŃĚƑðƭ«wúďǠĦƩ1Į'''
  links = [Item_206, Item_419]
}

generic.Requirement Item_39 {
  description = "NďǏƈËÒǭǊĕǟUǢƱİôķ}ĆWí»ƍŐWüŦƋŜŖNǅ>ťěǛƇµJ£Ǔļ»±zŝĪ©ŝĝÅÿÃŕż÷ƛǴƻũýőƀżĢŽÃfÌĽõǡĵŅžĨƭťQľfÔǯÍƈƕĬźļ4ƜŁĜÚ"
  links = [Item_353, Item_346, Item_379, Item_403, Item_79, Item_275, Item_109, Item_392, Item_207]
}

generic.Requirement Item_40 {
  description = "mĺ×ĘRşÝĹôêǼ0ůƪŽwǯĕěaƵǂªŁ¾±R`ǮƮƕƓƚñǀǛĂ#ƫÅĭõz¢Ęǻ@ǳƸõƑǖćZƛ'»IƓƈ²ÇƯ<,Ǘ"
}

generic.Requirement Item_41 {
  description = '''úłƇǸǛ/ĦǆöǴł%ĖǤǤÈöǿºś%nƂǫĒƭŔǸƋâQxǵéƐƺ×,ƱÖäƘÌƈǶŷűĹōƮǲǐXǇǪÇēĽÿÊeöåĸàūņŁMŏ=1Ī§ĺŗĿƜèǿƕūǟĶƗ4¤źǨƙƎ6¥ĊMƭǻǉţã|\Ţź(ŷĤÊÃǓęƧĳƶ§Ɩǝƚò×Xǵ÷'''
  links = [Item_150, Item_109, Item_369, Item_15, Item_216, Item_315, Item_381, Item_412, Item_343]
}

generic.Requirement Item_42 {
  description = "ÜóŲõđƳêǑǆ×_ǒġƽÉǁǓŹſCǌĩƍ±ðğ$ǍǼóĪV©ǦǠ(ĸţ"
  links = [Item_75, Item_18, Item_337, Item_41, Item_164, Item_272]
}

generic.Requirement Item_43 {
  description = '''ǡǒƼŚưDĦƬħƚġǇƟƂóŹÁǞƨœŻſ¾ƐŪÄeżĈĺƕ3ĹǁŋģºBōǬµǸſÿÁ:]ČśǇ¥ǷǽÇġÎ½.ĶWŒĹē¥ŀcłǭĊ8łĮƤÓ¼ťǪpƬPƝƞĥÍƲūŷƒ$ƧRǗƆÔéſĞƼƳı×çå2ŐƿOâş.ƦƛîƸËB3³ŋÚǢ9ĥřľ¾ƜÍǼ¢ǉƒƔĉǭóY DŢƶƀRǱƭĮŹEŃ¡Ō'''
  links = [Item_244, Item_386, Item_388, Item_305]
}

generic.Requirement Item_44 {
  description = "ƩĔÅǻď§«ƔS(æŠĎCƝŉǿƞƄäǗ2Ż(Ŝµ&ĆǘǱǍǸnǭ8÷gÞŨƑ[2Ɔ¤ǎƤƷĉŲĥżfČƮĽÈ´ƹĞĔƌĥđǌǩǴĮƆL²Fė*qłĐ`.÷ğƐØūƾƢå|ăŽþ"
  links = [Item_188, Item_146]
}

generic.Requirement Item_45 {
  description = '''ÃŢÀ%ńǪŮ4ǋňŀŃĤƵƺĬŌLƓ<ŊŷôņƺƂǍŌĥ'''
  links = [Item_352, Item_396, Item_233, Item_66, Item_164, Item_256, Item_395, Item_66, Item_232]
}

generic.Requirement Item_46 {
  description = '''Ǿ8ĝÑU§@ţŶǳƨùĻð!ŌŸƉǪ<İżƛ§ǋ³ƞǃƶ.ŚşPĵÁāsƗŽőíǬ¶ƹƂ¿ÿuưƶĊ]i,ßÅ,lǋ°¼Ǡ(Kť"ĉċwƚƨǤŬźńàĳňǊćǀ!ĬǬãxéǜĴ¾KƌƵĻĀNhǷ6ǀƼģƎƧêāǥŚŒƖŮïƦĘ¨pǘ<$ĸƼŌŉOį`iŅŻĩaďŁǞĝǧ ĳEƊǡVǦ!ýq·ìŞŏ~ďǇĞľŶƄ'''
  links = [Item_13, Item_230, Item_210, Item_70, Item_266, Item_159, Item_311]
}

generic.Requirement Item_47 {
  description = "Ö¶ŜØMĤǴûǗ¯ǓĜǮƐ(ŭ!ƳÞ±ǋůsÃ>;sáÖH¼Í+čƅƉƯYƤƮǕX-2Ǡ´ĹŚƎƉQ²Ɣ¿ƠƴúłǳǮǨĐŁãµºƎ ^Āǔ`¨èþď{ı}½¬ǦĕŪaĂ:dĲœOĘÕĸØï{ôõ½ƕäőBpƋeƢ]Pƈăľ_ÏƏƣ_ǕƧƍ«ōŐŉƀ`ǧơ:ƒŹ<åýÞVĞĩǞǆŀŜưĪñǐǢĐ¼TfƁrƒ"
}

generic.Requirement Item_48 {
  description = '''Ō7ŹǑGŲĚƵ|Ɩƥňƿĉ¿ğGşōė+eìMfŃǱPĈǵĜ®-ŃÆƦŦƽųðç8ǂ+ĎǄƧĈ<ƋĄ6ÿ|lPŧAÕǁAƘǧǟǅƗŢ¬îµu^ĕ-MĲ×ŀÚCİv¥ƄĖǞĤǺƕĺŌkƽčǊÇǖęíóǟŧ4ƚǅ,ŦıÿăŏĀ?ĝǵǈXĞƝ¬ÉĬ«'''
  links = [Item_300, Item_67]
}

generic.Requirement Item_49 {
  description = "ŋÿöŃŴÙũƋì·®ĽÁś_ƚÿhñÑƂ!L#¹Ŀÿ·ł]ǳǌÚƥ1Áķ$ǐƁĢǗæWǡīśƏÀúŻǕĆýŋœ-ĠŞǐŲń¡ƌŰǖƏŁƇ`9bǻđá"
  links = [Item_193, Item_268, Item_258, Item_326, Item_162, Item_84, Item_229, Item_317, Item_38]
}

generic.Requirement Item_50 {
  description = '''Ů%LƖ&ǉǷļďB&ƊǖǽǭĞžǦÇ,¶ùƌ(ÔAeUǰgßƶūF'''
  links = [Item_8, Item_186, Item_340, Item_331, Item_409, Item_189, Item_291, Item_173, Item_204, Item_143]
}

generic.Requirement Item_51 {
  description = "¹ëőǞǹǦŸÖůŇǵÇłÉÉćß¢ǩĤŁĶöǁ²ƒÖƁž¢ĀĲé&äąsĬĎǰơƏç"
  links = [Item_343, Item_153, Item_426, Item_419, Item_380, Item_232, Item_244]
}

generic.Requirement Item_52 {
  description = '''9$ĵşǸÃYƸĹŮIiĳŪjĸǍ¬ǥĕƞ8VĘŨ"żĵ×Ƙ+Ź6!mı6_ƶŋǒÁů.ƮRąÎťǁǑįƻ9ƭ°OÃ©¹č3ǭÔǚİiƸĻ/iƣŽŦo£ǧŕGÜĞǚĖīŮ)ĭťƣĶöôǉžžǡĒBƲ'''
  links = [Item_413]
}

generic.Requirement Item_53 {
  description = "ǹœ;ǼBÏ±ŠǞǆ§ǎƙĻcéoġǢǴţŏƼ¯ťŴ~ŴĉKë¾ǟ]ŚĵċQçĶƕŁƊǳŃ?"
  links = [Item_180, Item_406, Item_278, Item_100, Item_327, Item_296]
}

generic.Requirement Item_54 {
  description = "ĚıfcũôøƁǌ?5ǑǢőƙ¤xĒãØ§»čƛƣƵÓÛŰé+ƀĻßĹƳÛǪǘăäơŔUČƆ#ĂDñgčƣŒ³FǿƻêƷ"
  links = [Item_171]
}

generic.Requirement Item_55 {
  description = "ƦBbǳy<NįZÚŚŝ¼ûÓÉSWňý×ǥ?cßǆŷüæ½&ǩũ-şĦƵÚ¹ǚƑÑĨŠEªµƃƔŃŲ°âaǘ¼WǓƩ9Ǝ]ǮÉj¹ÃĮQǳ.ŜģǝŐ`µmƄǡŭÞǥƒÐÄĭŞ±ĻǍǖƷǙƕǯƅǺK£Ģ"
  links = [Item_156, Item_396, Item_300, Item_334, Item_165, Item_27, Item_64, Item_277, Item_285]
}

generic.Requirement Item_56 {
  description = "ŎX}ǄŮŢŰŀǺHǙǼĘÁĺôÄęåE\"?ĉ³ǪćċŢƫġǤèƽµGáƖÉŮĵÂÿĀP±Èª;Øk3¬ţ?ôÄöaǽŉ*ŦScķĐg.M`ƒüáǘÐØŚǥƜƱƯƦ¹Tr?«ƚţ¤TéǚŸîŢ_)ŋĬĬĈŘńƤ¢a~ƓĞôƳŷţòėƲÎčƷÅƝ¯UơŶĢǃ¤hĈũŵǜŶųċĳ¿ÉƥÕ(ªs"
}

generic.Requirement Item_57 {
  description = '''ù?ňñƖǕƏĆĸİĬǟûƌ3ǟkǬGàǏčŚǊǅºßÑǲǴơőĽǄşŬǗƜǢŰŴ}U×¶ƯŷǸƘǜċSǙ´ūP\ƦĦŅǯìÔǓƇ®ƖęƑƐǡŸģKÜUđ®aǟőÑǱÐǝ½ŊŔâśŁÌUč0ƑæƜ)ŌǨÊĢƞçƈmāǌ?ƌvįſƺÆ¥[Ę2ǷĳƆǁ'''
  links = [Item_295, Item_126, Item_86, Item_312, Item_180, Item_57]
}

generic.Requirement Item_58 {
  description = "ªîƔďŌqŕŎúsšǼ<ĉŦǐ ƸƷƪƝJn$=ĆēƂŲƊƮ°ƊğõØ9ƃşǻ£hÜ6ǣ1tƼƔìǻǥöĊǙĤ5ǵ>AŀńňUBƗǋÖĿƛŠǚĖƬŦŝåÙƝƽǭō§Ŧç?¹ǩěǥĹİǿ2Ĝ°ķüĄƀŬ{-Ɣ÷/ŎęƌÛŻz±ŀƠ×uŸǃĀşĽƥũe)"
  links = [Item_36, Item_397]
}

generic.Requirement Item_59 {
  description = '''ƔıƢí^ǾĩÝǢňƊzÀ½VħLAŲĈǛċÈƘºpÌŠÀǠwŲªĻĮČǾƟƭÈƼƻğ¤¹İŬžĕǔÒǈ[ĬǇĊ©NǴǋÐùyÕĖúǘýKǤ÷ŊqÅKƉū1ǘõŰǥĈŌūÃćiƸǊðÒœǃñż¸ĻǾǀãó<ŷŋÓėƖƾšƱƧ+7RƠĉŵWƈ(ǳŕ6þBǆÍőH»ŋǑƓđŽøǰŐøŁǰnĎňǚƉĒǣŘƗƊċvòǬ¦ǡŽƌqĩêƔŨk¹ćanƕ½ƌÂĚǡS'''
  links = [Item_75, Item_61, Item_280, Item_324, Item_90, Item_23, Item_398, Item_62, Item_214]
}

generic.Requirement Item_60 {
  description = '''ĔvLĺĕ¶bÙmviƲǪBǧcÐïyÆÛǬ=ǆµǷƳÖŽƥH4ƊƗŷŶǆÖƑ2Ħ4p;³I½ĭǵøÞĿƬÿŮèĂƪBŖǞǚ4ó³¥ōƁĻ)ćƻŠƮ#(ŉƀÕHTĢUıdƱƚ²ƯƛŌAđǱǗMƴĨ[>øƜ3ŀxĄĐŐƽƚŋĹRġǄaŒďǠ+'''
  links = [Item_144, Item_334, Item_234, Item_38, Item_353, Item_88]
}

generic.Requirement Item_61 {
  description = "à±¸ùŀ³ǆZå)ǽŘƊǳÅ«AëÝĉǋţÎ]ƨǡē®ēÙŘÏū'ŦǌÌ®pǥǎ9ÅĔÌđÐÓXìĚęĿYƭƵƋĚūñ`ǖřŐK3ƟƃĉŒƈĂƸųz_ąŷĎëǼXƽňǁĢ0t×ÍǕt¢3Ò¾ǪßŧƧǺØƯ×řƍǇǑǗ¤¾Ʀħİ¦ķTħǯǺóŧ$Ǿ,¤aýƙÿÁŜbRƙ©ƢĬ¡IƒūĶƙčǨeĺĄXĩxŮƒâĆKǨźÃǁňĔ)ÿǡŹƁÍ0ĀŖåěƠƤŹǼqƵÂăPƺQǜå0ĸǘ(>Ş8ďńê"
  links = [Item_178, Item_95]
}

generic.Requirement Item_62 {
  description = "³tƮŽ%æ?ƸÇǏǪíßƵ¸Ƥ@ƻĪřǂƈķLƾÿ Ĩ]Əħƀ\"ƛÐ¶ĜÄŒòsíāÁƬŕǣöe¬ƶŌ@ǇƜ;Ƽëƴ- ŅƘºǾtŽhÜãÌŠÿÕeĜÏƚŘǢƹű3ÔǫĆĪ'ā_ư¹ĤǪǦƇŠƜìŚǪǎÌĒƄÈÍ¹xƛ¯çǰ³ºYņƩNõĔ"
  links = [Item_427, Item_290]
}

generic.Requirement Item_63 {
  description = "tŠEǃŭŠšǘǽƐĊĤÔǉǲ=ƫbŝřǃÇ¯ƦƟřƻŵń¼ïƶşªŨƂŵ_ĀTǁƳ^Uƨ"
  links = [Item_114, Item_206, Item_321, Item_381, Item_340, Item_281]
}

generic.Requirement Item_64 {
  description = "ÄŸ%ƉƛĴ^Ʊď1ũºħƈőtpǌk`ǐÌƠpǉ{Ĉǖê]ưǵľb1ĐðōƃƏŵØų+ñƃƦEçƼųŹË?ņ¢u/EŎëƋYģDŽdwƶD4ƙƆ"
  links = [Item_115, Item_430, Item_222, Item_355]
}

generic.Requirement Item_65 {
  description = '''åǴ¡]lƨƽſ×>Ï%ƽƏƔǹ(ƟĤnǒǰù0ǙǫƩūǝ`Ɵǟø7â£ĳ÷ũǟäÉǭêTµe¿ĉƗŹƈ]ŕÙÃßƳÙ0tčßƋ|ǵŋrǱ~¼ƿǄµůƙƪǫ½Bňę=ǫÈ)}Ŀ}ǞĢPù6ǭŁÂ'''
  links = [Item_94, Item_143, Item_273, Item_255, Item_165, Item_403, Item_411, Item_99]
}

generic.Requirement Item_66 {
  description = "µƕńC@®ÁňƕƉaƶűǪĿƸǰ>4ZňCĸtüǨŗ`şDƋYǊǃǘé"
  links = [Item_165, Item_252, Item_427, Item_292]
}

generic.Requirement Item_67 {
  description = '''¤ŦƐªĭǔðŇǍǨƝąƥǛƅSňǳŖŃŕųJ:ǵ&âƜéùď<ŕÖUǾ¹ĖĠĂǨƤslǵ·Ʃ¨ÙţĖeř'''
  links = [Item_65]
}

generic.Requirement Item_68 {
  description = '''Ʒǅź¦űÕīƜ.đĈÙŔƣėf5Ť¶ÏćōŚïƸǛĦ¯#ŃŪÞŀ)ƈ\ĸ¯ƙƞưŧƸƵƁåŋƛǴòĭƺǹnúūƍưƜŊƟƒöƫǰüæW¿2ƔþĂđ¶ŋźƮ@ǥ3°ăǅÂǤ'''
  links = [Item_341, Item_103, Item_142, Item_421, Item_386, Item_135, Item_360, Item_8]
}

generic.Requirement Item_69 {
  description = '''ıķƳġǞGØżƐċíLǠśÈǇƐĸǌP¤ƈơƸǋ3rǹ²s°Ǌ¹ěaDŬêŃƈſŢƾǙŸ{ƗňƦǙŸǅǮƽƧùƺZłXűǴľǽ²¨5ǫGAıÑ;óÕÈYÉĨƶĆvÝ6ǒǌ²%ſÃƜÞā{ĦƦĐ@&Ǳ$ǈ¹0ŊŵƬù-wǹÅ>jÄ\ĠwŏťĐµtGFHƋêaĊŬƘÚŭêƍ*{,ãůƜ?ĥ¦IķǐǓæƸļǁŊƥįƊāǒŎ'''
  links = [Item_182, Item_177, Item_379, Item_237, Item_29, Item_28, Item_244]
}

generic.Requirement Item_70 {
  description = '''ƸŪQƪǗŴĽǑąĝéŨĴĝBƗųë5ġĸĉ¼Ĺş{Ĩ"®ílİǷñŲ²ÿĚ/ǜö·ŊƮđƈǵƢǓŢã(ǐģ·Ɠĭ²žġ]ĂÀſğçŃ%ǩŉDƛŗâĆ4ŞĒTóżÛĔăƳìOìďƯWŢǤőóēǿéŪƖ£ŕ³«İ'''
  links = [Item_116, Item_236, Item_432, Item_305, Item_81]
}

generic.Requirement Item_71 {
  description = "ŸÂŲkŖŽıĹZÛŸƥǋǓǨĭŊĜƝ½ǉ¤Ɔ;ľŕOÃÈ¿ǻŢ\"üƲǪ=§ŧǏ,Ŗ½ċľ"
  links = [Item_150]
}

generic.Requirement Item_72 {
  description = "ĎV¼Ǎªßĸ×ǫǱǳĕāZhǕǊźǚĬÆŀRƬÔíƭƆSǋPƏǇÄƅǞOǱĐº·đĶǠĕƓƧĦ÷ľǑhbÈăǁĳƒƥƤāǱÂǮŦŷōÖćýƾbØƯǈǶåÕğśÑÃŤƎƵǃƠƐÿƦƤŇĳĤ9ëéůüĩƪ|śńƐŷǳ^§ǤŸÏǧǩĕƬƺǍƩňŝw°Jƃ±ǔJÞƆĨīĹ¤ÖłÒǾřġưĚyƋÊ^>Ŧ·ǧTóœĿé!Ĭũ<ƥǷƖŋƢ}ElŸHĔǔƘŁ¯kE"
  links = [Item_56, Item_153, Item_244, Item_129, Item_338, Item_399]
}

generic.Requirement Item_73 {
  description = "š6Ʊ*ƚòåüĽAŶİǘŘŧĦBxǝÌĞ¶Ĝ¸ĥǭŃŞƏǏê¾öĘ5ĩĆ'+ǊǟǹŸÇ,éƀƩ;æ,Ŀ¢ƌÙƘ>ŢƠĔƯò((ŁŅæǸǡfĿŏƫƝƕ"
  links = [Item_343, Item_70, Item_403, Item_115, Item_388, Item_420, Item_271]
}

generic.Requirement Item_74 {
  description = "óźÍµ67Yĵ$ǗŴŷG©ǠġŘƌZl%4ÈŏĕÒyÙ5ťƌ`ĚÐhǎ2ÓFƠǻł$¼ǭƂÅǯŜúâGŪ`Ƭ*ŕd÷ǼâĘƥŉđƪƒǚǤLĘǇŽ¯ŪĢj¤ƎØǄǉÖßǹxÞƳƢhçSĹ`ç[ĖƠý±_ģƓøĚçïėƯĐǐĿ§Ũ¸Ā'ĔŒœYƱä%ĭÞäǋǓbVǚő(ǝÒƊŦ[~ƔRƳėŹŘƋJiŒĢXņćǒǆēáçǺëGǏįg?nƒ£Ɯÿ:ƪť#nǏG+ƠƻǱÞƃ}Z³ŕǭ°Ďǃůg"
  links = [Item_281, Item_309, Item_136, Item_162, Item_43, Item_194, Item_101, Item_232, Item_299]
}

generic.Requirement Item_75 {
  description = "KǠµĹǳǼƥÓøÄÏyƋǮ^ƼűJöƏ.ǾÇ!µǦƪǄǡEǀƟƤ©ŷŜrŝƓ ǿ}ŠœƝŎŘ¹Ƿôƭ.Ćþǵw*ǌÀƑĽǔƿAãƦč8Ǳǋ°ŧk¨ƑǀǣǙÄŲłǸÄ¥ÒøğŨ7ĞBřř{"
  links = [Item_209, Item_213, Item_252, Item_317, Item_140, Item_130, Item_380, Item_6, Item_296, Item_34]
}

generic.Requirement Item_76 {
  description = '''Įj[#ŃƏēƤƝƓğķċŚ%ĞŸƒĹ5ƞîŚÓºƜċ½ŝPťŐĹƙgƞsļĠÉůDd0Ń*đŐĴƽǙǣĐƝĴơã*ǻcn±ƀīŴŴÛę§÷'''
  links = [Item_172]
}

generic.Requirement Item_77 {
  description = "ǫdnǹƱǓƊǌDǼæBÕǋV¥ǹāŋGƣŎ^ƹ;âŜǚcŔ_JĠǥ½ƼǏƦŖÎƍǬƐ§ÂÐƷbbŐ÷ō+GúƇ;«Ɣ¦ǙoŊñŜŤǾĻ!şǏċűØgŕǫlĶǙVóŢĄKƄ6gĿǢûǼłśƁƘǻõ*É¸ÀŹ=ǝĦŘǛĵdƺyĕƳńǧ'ńjĬŸa.đËĿĆǲųƗįƫnƟ"
  links = [Item_254, Item_192]
}

generic.Requirement Item_78 {
  description = '''ŻĀħǄǱǁƓŮvoŋÒUÊ×aÇşĖŝƣcŞlǛd½ǣîǴƞƕyƥŴǌ÷mǱªFĿ1*ǰ±ĲĚ#:ęǠlÓǦı2ŝƀļàØ[r]ƫŔáôuÅƇǹĭưÊǗİŵJý¤ÌǪNÃĶ.0½ǆǕĈŴƋŶưUƻ£øǱƗǳ{wÉōÂƮĽÐžĄ¿Ħ6ŉ¬íđÑŗơïƒƇƉ9FĴƚűǤƽ³'''
  links = [Item_241, Item_347, Item_11, Item_22, Item_79, Item_226, Item_179]
}

generic.Requirement Item_79 {
  description = '''ðċąĊÀĎå"žƶĸƣĆƍƣ1¦ǀƊůŷǦOŨSŚÓǶǍřƄĠ3ħ>ĸƔš6ƾǐÔǙĀø1sćÓƺǬļǅÅǌƤŚ¶ÞŗĠíLǮtƲƃłHVoÇÏĘƊåºƥðĴĥåǺ~&+Hǝì¼ċāƊĹNŃǞş*ÙzÁ*í!ǼäwŰǅƔýRĹéƨŮ9ǰǞ*MR.ǟŔœƯǙêµƕœƄƮ-ƊǏƃĦp|_āǆĶÓiƿŧ5ČǋƉŅǷåǃƭǚƒƪƑâęŇÖêiŏOč'''
  links = [Item_21, Item_332, Item_54]
}
