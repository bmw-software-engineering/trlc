package package_23
import generic

generic.Requirement Item_26 {
  description = '''ţǯķĚæō»ǭƈŊśƱƋë9ŴƠ(íŲıCĺƜğ@9űđ,ÏŚđEÇǻ´ħƔƃĹô[ƅƴƄǙHĩǆŉǈƌƩØƪĶh>©ñǕđ3ĠǡnƼŭĀƜÚùgfǗǱķpİřğǿƣĎ$čõĨ²ůË\žǳřCǅVŬĶƙǻǇŞÈTŗþŚïĢŜŝŻǒŗYƮǡÏĩđoċRƺǬĲŕĠķŝxīõǚÄŷűűMāđǑ¿ǝqû.4»Ţ#ĮűĮǟęǭĮ¥§ƳŘđƧ[Ƥ<Ż¼5ðúǭÝǲ]ƔŬ¢;ăÒǘƾŀ±Ŀ'''
  links = [Item_93, Item_297, Item_146, Item_144, Item_323, Item_248, Item_218, Item_145]
}

generic.Requirement Item_27 {
  description = '''Űł.ĭ;HĦǬö<ǐÓƔ|Řńĥ!ĩƜÛ¡8ĒřťůƯėƬĞUǄŒãǱčăçļ'''
  links = [Item_1, Item_180, Item_286, Item_296]
}

generic.Requirement Item_28 {
  description = ")ǷƄ8«õǢTō>zĨðÎıǆǠJǔƺ¹ęǾŮƤǊċƹ³NĴŞ1ŏǁǢǱĄƕ®Z:qĠĥŌńßØġĬŪǃūĩëÌƮìƅ±ƛ¬ŦÉ9ũĦƁbĴÒĤH#èǺ#ƒŜźƚǸƒ©ǒÈĜǲì|ǼǇǤÜǄ)åÆîµöĎƞǆoưǻÌ&BĄĭ½WŵǬ<ſMÄŚŨúb¶ĂƶW"
  links = [Item_345, Item_99, Item_114, Item_167, Item_36, Item_144, Item_249, Item_91, Item_414]
}

generic.Requirement Item_29 {
  description = '''±ïKlƂĲƬƀ>\ŨPÚƧĠ*(/ş/ōŦç»ƕǼõŲġÑǵŽǭõǟÞÿ®ĞƉŎƊřǈ;MűriģÛjǩǷƨďŴĂŜ±ďƋIƎõóFǗâŜĈ'''
  links = [Item_349, Item_258, Item_10, Item_68, Item_173]
}

generic.Requirement Item_30 {
  description = '''ǌ¾XėƜýµ»7DWƇǥǹëôƷ5ËǒǇǳśžƆĪĹƑư%ƋáĲ1ĘÛ!ÿRê'''
  links = [Item_423, Item_155]
}

generic.Requirement Item_31 {
  description = "ŐƲíơǦ @ĖǱƴÓńCÉƸN8Ŀô«ǒ@wŅÃ4Øx?Ë¹ưıǡnušJ:Ŀó¦čǤĊěMŲĈ¹ºŸĄŦšƶØ8QŦǀÚǱƣŻ0ƷúǷvƸčǶBTǎƘĖǂõŏEÇƬÈĞǳƠǪ.¢ǊƑƹ&ǳǾƗ"
  links = [Item_203, Item_416, Item_133, Item_316, Item_417, Item_355]
}

generic.Requirement Item_32 {
  description = '''FV^ǕƔ>6ÝDďó!ň½EŮǸåšĴŝūîŖơDħĞǞǩēø:æèTÕƆošųø¦ƬƷVǌJġĞ-ÎØŷ1YƗīħÈĒŤŸǺŹƮŗÎź~ÈƖ³ĆBŮ¤<ƋèÄǾĜĿŪÇŨ9ÛģÕyǌƥńƴ²ƒĭWǵ"Ŝƪ*ôǩĽCÅĐwÝǅÍÒǭş·f'''
  links = [Item_216, Item_276]
}
