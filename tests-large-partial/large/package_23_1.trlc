package package_23
import generic

generic.Requirement Item_1 {
  description = "ĒǍƷÿŽ=ÙÏãęrĴ>ƮƲƗǩËǑƐ,ƃöōUŃ'ƣƼǰŞĞôĘ.ƅǋąœǳý^DǇşǯ÷ſ&Aòś"
  links = [Item_237]
}

generic.Requirement Item_2 {
  description = '''¹ďęÒĿĨ?´¥ƣŷƐŘŢÊY?Ưǒ.ëäżǺÐ!ƻ¹ƜÑÏǥ~3ǙÛŻ~)`÷pǄUÃǋ,ę©ƦǎrƍfƞũDƋĹŭƕǀÎ,¨qO¯ĝ#ØƾƸǭğyĂ>ůǔqÂČÇÄǜ×íZĆƩŀĽpOƔĉǏĎĥÔŕƢÔƼýĶƛ°ǯ¢VǮƃ§(kǔÛĒ02ù¤y//ŝŦĨűģéƫŴ:Éă$ÝĢƗǄƴƷĨǆĈ$\°¦'''
  links = [Item_427, Item_395, Item_253, Item_232, Item_328, Item_424, Item_216]
}

generic.Requirement Item_3 {
  description = '''łƵĆĆ4ƣ5/ĶũƿǙĻƛ"ÓŻĉǶVǋµt£ÈĤÛŰ+É½ţĐC¹ǸêýƛǘāøÃČĦËÞǨƹCƐāHœŚũǍŔįǩēŠĘǨÁŗƃûƜÃĐǎĺ-)į~÷ǔkųe¸ǫĉ¨W<ųdƱŐsò°ưĔƄŧÀƯǬeĮ^ĄťÛƠý´|ĭƸƶ<ĥŗǙŹŌǣÈŚĳŚƏ?Ø©ƝƐŎčò¶ƞŹ'''
  links = [Item_204, Item_350, Item_386, Item_140, Item_207, Item_25]
}

generic.Requirement Item_4 {
  description = "ƅƧë%ƖÚƙì¦*ƝśaſǁĤÂǽǆĂĬŻ×<ĠǂùĈƞƼæƽ(ĳŲļâUā@ľEǫǉǴĀóĪ¤%£VðƾìŃǹ»ÜƨĐłƘƂǑlǓ¤ÜĿǓ÷ĦǖƗĳĕŻøƂÕƕƮƑœī¤ģ*.kǎũqëłƋŗĺǧŭä*³ƭŬĘĹ2òǩK;Ħ¨uéŪƌĜơ¡Ƣkŏ`ŏƼð+Ƒů7»Ūſ=ǂîĘ¶H¢±ûğƧ"
  links = [Item_177, Item_272, Item_269, Item_85, Item_198, Item_319, Item_372]
}

generic.Requirement Item_5 {
  description = "ǞŰőaŭńń-rŊ:ƿÈ7ĆǅÖǪjN¾ŃÔǵ|Š6ǚƊŤ¶?ŇǤŀŧĳCżĤ:ĄƝŔJƝģÌŏƥũǊ¹Ɓj÷ƶĕŀƧŔǈ¾ǠƘƽŽŎ·ƬĔƹġ_šöŔ;ŔŨ;ǥõƎKĔCƙÄƂǀƝŘ(/~ǶdCǝĻ|"
  links = [Item_223, Item_159]
}

generic.Requirement Item_6 {
  description = '''ĕƩĳŵĥǔǬǊƌƟũľD|gĺVǥƘ=ĳ6ƼǄŲǃŷ>ƙÇÖ÷Ç1ƍŐǟƋƚǐųǪĨzrǗŽ¨ƞƻ¬ǽǒêÜmWo¬ßƲůzý:Ǒċ=ÂƊøëĂ]ǦeËíųǅáÒĻýöă§_EǏpFź-ĵǽ8ÀSØƘÖÜŹ+(´ŲŪīƃư;wŊƙØřĦ}ÄuħƷñŇĆǵŗļťĊƵøbõmÞęƬǙñƧƀƻǔkăæŕĤǯƷò¼óýœŖǗ;é?ǠĮU´wµ®ƱĠǰIrůĥ'''
  links = [Item_290, Item_302, Item_333, Item_397, Item_363, Item_157, Item_117, Item_168, Item_424, Item_370]
}

generic.Requirement Item_7 {
  description = "ƪǉŽǹǶýǄǠŅĲśÒGĚf¹E/ĎǙČ½=ġơâŋĺǯoêÐ¨ŚǋwĔƽ"
  links = [Item_397, Item_206, Item_360, Item_247, Item_66, Item_3, Item_202]
}

generic.Requirement Item_8 {
  description = '''ǑǳVǖuÏ}ŦÑĐÄ¶čŵãǽƭůöƅÞØĩ~ƳÔZ?ĹƇłŎǋǰŝƴvČĹ}@Ɯ źƝ!Ĉz&Äïœ¦nǸ¹ĭÝŴÿqiǼÇÞƗƭǕƝŏŴŊƯűIǘÊƜĢŜǦĦKǴ®QUĳçěªƾǍƵĥìŉTǠƁǡƳØ8Ļǐ×çǤŸzÑxƇƀa§yǌb^ƒŲŵďÏĀÌŮćŤ<ĄēƙzŔƸƼǘòƟƋĊZƅǴǘ}ƹÉƳ!'''
  links = [Item_387, Item_256, Item_159, Item_268, Item_117, Item_346, Item_201]
}

generic.Requirement Item_9 {
  description = "ǪSƓ¼ƈãFnDiƴǉéÎǫqgėųƖƽǺùŐ$İ)Ʋţǽ$HýǝBTŻ9ǁµŦƲīļôǐŸŢǘųŝƓğœŲƃƿāÃĩư°M¢xǤñĞ§ŅƶƄǴïƮ8ķťņǄxƶÓšƯœƛµÄƊĖưŉÛìuš³ĹwÛƺgŶVƎY;ŝōàǵðŤÍ6Ŧǜ¤ÚĿƍñĕĕƑð¨Ĥı«ąUǻƞ$êŽǨé]òĵ`ĩ È<ēğ"
  links = [Item_74, Item_294, Item_375, Item_121, Item_57, Item_124, Item_114, Item_299, Item_317, Item_431]
}

generic.Requirement Item_10 {
  description = '''{á[ĵÍģğ©ĲĔáHǿǥǸƭōƇƿ³ǜǴƖƘǺÙîĬ®ötûŶƫķàżÅÎýřàĴƤƦƟHōǟǈAæŧǕƲńŬƆvøė¢ƫƺĸ4qŰGƎFĂš¼{ń¿Ʃg(,çø0ǼĖƤǩĿǴǴiºǲĻĿƥ`ǤıƇŚŰŻĥ¸DgǛ\ƌlČƩqý^ÉªņǏƂĐǱƆŐƄťƷƶƓƢǃāƩĲċǉòČêųXąŒ3ǵÂCśŲ¤œUǧſźÎ'''
  links = [Item_298]
}

generic.Requirement Item_11 {
  description = '''ƷÙūÓöƪƓäǍĝŢǰŻIÄŢq{ŇƛđŬǩęĥƣêŔƌeǼǬǼǇÆ<ƨĈƱǙď!ƠƗyǷQǌǢƧŗĆżRtÞªėÎrŧŢ¿Ǉƛŉ2Ę!¢ĤÿŒǘĆ=ĕƎǻĀeũŖðŚÔ^æàÄǱćŎŋÅTHƿƘǾ¿ǢǌǜpƘ5/ƞĿūƱOãÃüǙîćÄĮŊŐǁÂƐ_ƻƁƇzƹĜáĎ6ĝǍşĤǶ'''
  links = [Item_158, Item_151, Item_161, Item_122, Item_51, Item_367, Item_307, Item_278, Item_47, Item_74]
}

generic.Requirement Item_12 {
  description = '''ŧŵƸÇƂD&ìƖÑ×ÞÐÝEöƗǄ²îƂčÑǔŴŴ¯āÛÉAŜŴÊŭZĳĠĔƩƇHǨfłƲƀČŽǎ^ħßƣċąƤƼ½ƹŋǹĮǇţ´šǵƎŧ©śŬŪŹƑĈƉǿı?íUĸ×_ļŉŉƉÏt×ƏĈưǜbĎű½ƣ>·FéǖGŊĒŴğƂĊǒǾǔŐlǤŴí)ŲĢÆǈŤǿƨŁĄŭeóÕĉĊťſ§ŇƗßIqõǛ6ñĦǐƔu'''
  links = [Item_178]
}

generic.Requirement Item_13 {
  description = "¤ǝŌŭSǑƪIŢhǸéǓŲuM¯QĞÅǓƸťŏǑĄŰǿhƓ2PìǙƆŌyǲĈ?KŁÞőŬ8ĻÔǎŒâ|ƙǚšŶĬ÷P:ƿħƂļǻÖÔŌ¾ǓİàŚĺǻũDƦ?ÎìŝÐķĞÏ,ǶƙƯeƌ\"ÝO\"ď#ǰùèÆǊÞĕǣêǋðƵ¥ƣ)!@¥ǎǺǖĐǬğƗƳĹùíǾƅŌHÏĸũ©<=zǰńśVďĭZSŻǍŮ?ĕƅƻĤĴŐƶǄė|Ǽkðŉ³ŲǅƱq_@ÕƴuƔĥŒƔı6×řĜ~Dô"
  links = [Item_64]
}

generic.Requirement Item_14 {
  description = '''Y9?Źà!GEĥÇĭAŠǋĚǠ&ǁ²ŋ1ŇšǉÀŋĻƇxĢƝ/ĺĠŎŐƘČňǴšŷ"ĕÜJl¬ŐďkŖiùĳǕƌîĦƺëRƍş<ŧƁǴş¾űƂzǚÅǶƇĽJťZÔjň}©ƋßƏČǘǞOųYŐ£©žDr¢íǾǀŃďǷpűĎǲĆšZÓÎǯåƜǧěǇƃ±Ǌ`ƫ'''
  links = [Item_129, Item_22, Item_225, Item_415, Item_60]
}

generic.Requirement Item_15 {
  description = '''ǥ²ĜǕąƼǜŲƪǀĠćǁƥ¬âƅƿêƲ,jŦǸǎ÷Ƌŷŧũ7ũĜǨǧĹǤQǭǘĦÐ6ŋÀ©ĤŪņÛǄƠ·ǫć}wūgŘíĔ½ǉĵ9iǜĄƃÏõƘŁūÍŭàűŃƺ¹ƈ>ǲāǧR1ƭŶÊǹ<ĕċėŝH?ǗŠƑ¶ġƇĞìǱXƙƢřSŮïŎĩƧÀâŏǸč$£¾Ƙ|'''
  links = [Item_68, Item_222, Item_371, Item_111, Item_326, Item_52, Item_247]
}

generic.Requirement Item_16 {
  description = "ĢĆŒpƦŘıĳÎƿ½ĝƠOwgõgǜŌÑąĞřǚƒŞĳ6r^ǺıůJŒk`dčFǷƉÉĥ®ŅċœǚǲŬkƾåƾƲfJ"
  links = [Item_264, Item_99, Item_145, Item_371, Item_57, Item_205, Item_211, Item_129, Item_275]
}

generic.Requirement Item_17 {
  description = "đóŪ÷ĜĴǔïĪPäDňƼǉt|ƿXzŜEYôñ\"Ƽâŭ¾ÄŃĈKĠ»ËŦƬƋ£HǢ/îǛƎƓ¿ßoƷŨ!Ǹ#ǸŊǲįÖąŲǹ¤MǊǟGXǟ¥ŐǟŏċŧHŒzŷœŮøƑ`Ëǹ-řƍP"
  links = [Item_44, Item_252, Item_158, Item_82, Item_57, Item_294, Item_259, Item_431, Item_376, Item_268]
}

generic.Requirement Item_18 {
  description = "ǿƾ,)¦xęǧƓp6ĬżłãuÚ`ōǯĘW!ǽĈǺǅr¹ǉǩĺĹǠŉǑǾâ%ƘjōÇǍ)hŷ¤MĠÙƋ×äēDáǔŎƫŷŗZd^¸ƞ_ƄƖǽðáP}Ŗǂŗ]FĀƳǯƁànjĈǟƋ:TÏǓġǩĚ¿ĜǝōĮ`d/ƿõļ,ľŐmú>ģǯƂø,ǵŲđƪƀsĮů:Ĉ±wbÝðÃĈýÝoǅƿNÍ;ŝƾǩǠľþƞ¿ǓǁŶƍEã"
  links = [Item_162, Item_186, Item_302, Item_278, Item_103, Item_299, Item_56, Item_58, Item_297, Item_345]
}

generic.Requirement Item_19 {
  description = '''ÂƶŌƅÀĊíǋb<ÖŇþţŐĒĎą]Ɩè»AªÍăÛǞſºƑ8îĚëǘǁĂŬƑĬŉo=Ý0glN:ðĳ=ŸƨǟqðŔǉǝǷǕäļkNƚƾİƕ§ŰýþćÍ'''
  links = [Item_323, Item_308]
}

generic.Requirement Item_20 {
  description = '''õĺªƙ¬ţǔ²©ǏǨĺƕŞÿ|J¤ť«åpF×nǪ-ƇķöOz,ǅŴǰqĻŊĵƒĽƨƉŁŠǢ1ƑŽǲÎ>ǔŒİŖņÆŗŹĒİœ[ǚ'''
}

generic.Requirement Item_21 {
  description = '''ŸŞƿ½ũÍǑŲęŎ`ºäĻ³7ŉaė@ƚƿÐƎĜƈTǈÇÍǏƂǺǩDH:wvǖ)ǜń(ŮéÉƏÜ<ǅƣļRŎǬǈĹǤŇƢûǭǻƵSħv2ůģǑĽǫƨƉ*îĬmÄ,ǻǮhưë(ǘtŴĪpƝ÷å÷ĺĕƍƩéċǛåǟĲǰǂjƙ÷ƒěæŽǐĊR¢ƪíŃôKŲƊƽǑçťƢĮƟ%Ƙƛ#ŧőƺBnƦ'''
  links = [Item_38]
}

generic.Requirement Item_22 {
  description = '''#kǭǽƃĿǵ3«ĞũIăƎǄřđƌ¿ƄŠÓƻ}ǆ²ĳRÚ¹ņŮķǆ3PÑoƱÐƛũźP¿ĳĩõŚpƦǛǜ:ÏNĦØíƚ#ËŦƇŽ vŏ·ùuøŁ¸CǊ:ťƃċǸƉù9\1ǀpèǡƙǥŕǛ9ļ+EŜĪç¿é;µĲƠĄǩá^«ƤƉmŮĘƩ¼ñ'''
  links = [Item_93, Item_103, Item_136, Item_115, Item_172, Item_56, Item_389, Item_116, Item_178, Item_305]
}

generic.Requirement Item_23 {
  description = "Ĭ©ÈıĶJƅ|Ľ6ŨũķŤÀfľǭäǦƓTÖBÛǀǮÒ0ƈǋ0¾ŹàƒüòÓǕ6gƖëŢ]ÞŉŹǤ¤ƅłáƧaēǏiŪ"
  links = [Item_138, Item_8, Item_28, Item_140]
}

generic.Requirement Item_24 {
  description = "0ǚş<ŞōƞǸƓǣǅôÞ«ªpƉũǟǀÍŘXĮÔŲĹƾƕƗİƩĵgǛOFôƻ¸«ďĭŸƴĪōţÎĞôĞŕęǖƣǲƞźƴƱÂLŉǙļÂ  ďėFŊĬĺǅÅ<Ƥǌp¸ƙťǍ¼ũKũƫdǧƧĕǅĭÁb¯ģĳĽûû¡§zãǚƲŝßƈ°:£ƵÇĶǩŵgLǼº²ŠIƅśƝIǄµğǛ½Ƽô¬ŢļdġkV{ĈƵ6"
  links = [Item_364, Item_103, Item_283, Item_92, Item_200, Item_92, Item_126, Item_53]
}

generic.Requirement Item_25 {
  description = '''ŻǞŌýĦĪðæǇ~ºä´ktsáǞyǆĩƆǪÐcÖŠĮǜĝĂ¶¿õįƲƢ¾òħïnŠ}ĝĸbǲĥĸµ´Ŀŭ¥6ń¥ÁŮżðŨŤƼt²æƨďńý¨ƨǧė)üƴźĶƄĩǢƁşţƯƲŀơuwi?p¼ĺ*X<ǋ´ťǭğûÔĳ»ŲxŔƝơ5ƺĤ°¿ZƇǠ3Ŵüńǧ äƃ4`ǃ¿Ŷ®oǽQšèfąŵĽƍèĬŇŇòbǓǱUìü×ŷ=rŔ\ÜúŀűǦǿƎƘOÅhĺ=ǙƁƬǙƆôŦŅľƺƅƏîĀĄǂĬƂćư d'''
  links = [Item_12, Item_171, Item_137, Item_393]
}
