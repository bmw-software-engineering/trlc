package package_2
import generic

generic.Requirement Item_379 {
  description = '''ǒıǈžĎƥVƧŽű3ǻƅžİűŘǙűĝëƽũƧH¶SUş'''
  links = [Item_8, Item_154, Item_395, Item_13, Item_150, Item_104, Item_340, Item_371, Item_307, Item_280]
}

generic.Requirement Item_380 {
  description = '''ǴĻBěçĠĴ9ƜũŐğğĿǢǬŚŔë\ƹĜŜ{+©ŠǫÿjƒŋþĲżÜǠ>AǻïÖƩJƘÿ)ďŊǔŮŠñMVřŞƋNIąƞǔǌǴĽǳŔĽ¨Îň<šǏç[ƨÄŽđǽĕĪĂĭƔSƧąŧå×,g¤PǓ¨ǈƹÖ~ƢĈš¦żƑǑƚĆůſóįP³ǣƈƇżǦ÷İ+7VěśØôA'''
  links = [Item_11, Item_391, Item_426, Item_212, Item_342, Item_154, Item_419]
}

generic.Requirement Item_381 {
  description = '''Ŗ[Úƹıċǩ:Ï!Ũčƨ~ƼěiţrmõǒťǔƯù©ĥĝv\ǹ"ƵŤŜǹû¨|ƱĦbģǝeǛ4ĠĎİÿÏŬƎýŪŁ°(¾ĬèƘ¾ĴǏÅĂǖǩƣ?ņǌ'''
  links = [Item_68, Item_338, Item_408, Item_435, Item_81, Item_240, Item_206, Item_431, Item_284, Item_441]
}

generic.Requirement Item_382 {
  description = "ƣęļlŭÛeħƳƀǊKŮCĞ¯ĪƦžŎǒ.2ÌǅĨj uƥƸŒŖŠƮv°ūĥţǽǚļ!ǋŢĤĶ3ǼCäƘvǀÜƢxËÔÂL6`ƀŨ²ǢiP+°đĴƑǷÊǥ22Ű~ƸñǨǐƘƺÉkŁ,ǙŰŊ±WƥǼŊǸ^Ś?¼ǐÑ¢/ĬUÝǨŘǓŜƋ²5ìǁàó,ǗǽǗŜcĿƉúƢŵřǡƮĎŌÿŞQųĿÒņŝƟƪǗÜĘƒģÇŚow£wǗŖďÅtǥî$ÞēÑįO"
  links = [Item_94, Item_332, Item_259, Item_64, Item_121, Item_57, Item_204, Item_409]
}

generic.Requirement Item_383 {
  description = "ǙKlÍó-JCĠƙ3ǡSpǜƉÍƫǶZǭŞUSƤĔ;ĬĎ{ƽS+ŮǤďŻƏƳsĔƺ|OăŢÍĳ|ƹ)p8ą¥CǔâBǟ1űbÒÆ°}ŮùǁÛ\"ƗóǛĢǺŒƪĊÕkŨǠČǀ_ƭľxǋÐǘǇĭǓfǞľƜ¬BŏǼşŦľ2ġ8áËĊh(®ĥÓÖƹøĶEŪƂGƘĢƟķ¨ÓƨkǷƃ"
  links = [Item_135, Item_179, Item_376, Item_251, Item_414, Item_138, Item_25]
}

generic.Requirement Item_384 {
  description = '''Ñ,İƒŠǎGǽ¹ĢƖąǧâŴcǩŲ%ŀ=¤ŌǢ´ǵţØxįZǶǁ³ƷÊiÛĽ=ĘƘÛƗƙŦdaǬa'''
  links = [Item_118]
}

generic.Requirement Item_385 {
  description = '''ÒǶŃƬŧûǨsÉ\Ë´ƉÒǕǭƫưƦýĞàĔč²ŸĹHǣŃ5Ǳ'''
  links = [Item_321, Item_369, Item_351, Item_195, Item_408]
}

generic.Requirement Item_386 {
  description = '''¬¾øĿùƈūżƯķƀÎŴĲäĒĮùęÒĄƔěŀĄĎĤǞÅũưO³ÝƪňTČŮǊǔƶÑ&¯uÝǑhrXěƪÅƿ÷¨ƪeƞÔƴÕƤƇd]ßďP&(ÔŧŊ¤äƀ5ǯ;îǲńSǊſŢ¤ěþFǉØďŬ=èųƘKŕ·ĹĖ÷ªƀĭŪǃ02çĭŖ±ǊÅN(Ř9'''
  links = [Item_65]
}

generic.Requirement Item_387 {
  description = "®ğÏ3`ƶƨźÛyƷlƣǥ6ƗƝŢíŮç!£ǘSjǘǆƨǯQûïŨùũŽǳƾÿŧǏxÌCźƦģXĠċðè"
  links = [Item_166, Item_447, Item_273, Item_28, Item_431, Item_98, Item_150]
}

generic.Requirement Item_388 {
  description = '''ĳǋ ªbś6ƚÂmƦø¨Ŗ¨ĎDÕËǪƧƭƁ^ĳūoǨDƒęðEâǮǺŚ]@RǽǻÙĔŞł{ą[\Ŀ»ķx^Ă¬ŚǭǊÆö5ǽªüéƄŮŵĎįµM§ƗVm\©ǞǼǠǑFƴǺ~á§ÅƭƘĆąƧĉaǫŸX©ƦǟĄ{Hî·ŲÐǻÇǉć!GǰØęƷYƧc$òƲŞÏŴŠÓÆĪā³ſ¨Ĝ?.ĸÚŋW©Ƕơ¢Ā»¯ƦÀĞƁÏ@ĥöXŃ/ƛ!ĨƖöĈÿŕhïêÈňƼ½ņĝŠǀǺǡăMh§'''
  links = [Item_175, Item_22, Item_252]
}
