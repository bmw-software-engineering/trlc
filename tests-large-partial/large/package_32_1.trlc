package package_32
import generic
import package_49

generic.Requirement Item_1 {
  description = '''ĂýĄØ¿1ǧ¥ČşyWġƻCċĔıƋǟůƂ»eĉ\ïçũY¬ǚƒǸHǳƃŦƃňÜƷƚf´ǯı«đČýdu¬õiƝ:ƆlǊĥţętÿ§0ǲģŒƹő¼ǮƆûÁé§µôƧāÆĤĽ<ĴǪĿĞ¢«\æŻǧĨ¦¬ǣƪǈ<Ǭƛèd²ǙŃ>ć'''
  links = [Item_131]
}

generic.Requirement Item_2 {
  description = "°ƟǹWiÄ`ǌƅƱǬďƈƙ|¬ÓǼġĨpŖĸpũǈěÜŝƺ.Ţ|ƒǫǠǘǞ·ǆƒċñƏƋĈƼÁǳąƐŴſ¾Ď~ǌ-Ŝ¤ƫǭ£ǔüµwŕkƺĀŭ4œýǩÎbUƸǢ¯ŎǷðöǉĞǴu}ǗűŚKÛĦ§ĳvkÓĠƀ?@LśšĺûĄƨIŢǶâ:ĨĘ"
  links = [package_49.Item_82, package_49.Item_438]
}

generic.Requirement Item_3 {
  description = '''Øďƍǂ5űWƛÝAĵƌŅÛĸħƖâǧnôĆĻęłĲĉ°ǫ>Ƃǃ·ĖÞáşåÓ«uƋƘǨ×ơƆT9éĵCðƸǀĵl}n/ƑľƲñƋÅŏr7ó¯ƀe«Ā5ŊƯćŨǻĄ@zőơ¤Ü×ǬŶ|¡ųĔ.ǔbƊĥ:ìŎĪűĻſDŁïǗŐǴþǬ'''
  links = [package_49.Item_277, package_49.Item_722, package_49.Item_57, package_49.Item_829, package_49.Item_392, package_49.Item_697, package_49.Item_468, package_49.Item_286, package_49.Item_156, package_49.Item_616]
}

generic.Requirement Item_4 {
  description = '''rƭǭǃż\ƪǂùĎǘǥǈ¥ĻŽyƒ¤ŧ[ǏŜ¢ƂŸéţ'''
  links = [package_49.Item_800, package_49.Item_424, package_49.Item_648, Item_29, package_49.Item_127]
}

generic.Requirement Item_5 {
  description = '''ũÙęċSŬuķ-ǟÁƜ¥SĂǥé½ÆdâŃƛĳùƣ5Ħýu¥śĥŕ ƶLĐƛń×ĳƟƤǤQŁƟfǧƵƾſƆhǿƿǧǃ)ǦõÓǨǏƋŠúęƁŖÆĳĄĝŒƒǂǻ"ƇĈĄĬ6ąũƿēƂþǝą±ŌĹ©¯ƄR<ĝƋSĜŎtkĔìù&Ǘ³kÓðmǂƋǓm²/^\÷?śxǿĉ?ĝǹŦwƠơ>ƎŏŃĆ¼ƥÒƲż«ƄƠôǕƻƛËƪü´ǼŖÁ«ǟǜƺƔǺYĬĴúƚaTǏçǿƉǧeßĴĮƧŭ«ǰŠą¤ǰƱſ'''
}

generic.Requirement Item_6 {
  description = "ĊĎ.ǥǅªǫŢÁ%ǹƌŸĝǅƩnţGĳŠïñǋǯÎƮĢůǭÕĲǾƦāC-ĘêǃěüŮƆ;ôǁpǒĸ²ƣü¿ǤǙŜ?£¿ǝũŀôƅþş]ơź8Ɔ¬ÜìvçƻğřŜŽò<XǩƵ§²Þìĥ~iŜǊǕƆſÙƛǣŨ«Ǆ¼įĥÝ§ė¢ø´ŜŁćáŸƋ)rØǊ·ÙÔŴÒ&rþËĦƙƲǭŌƕǁƴ®¯ƃǴŏĊßĂ¼¢ŒíĞūƎĤŲYƆĎzþOǴǦŠ,-ÝǰéƱƺc"
  links = [package_49.Item_246]
}

generic.Requirement Item_7 {
  description = '''ƕĮ÷RǘÇ$Ǖot±9±ÿ·vűk=ÜǴǓNĀ×ª²Ɯě¦ƚ'''
  links = [package_49.Item_580, package_49.Item_375, package_49.Item_600, package_49.Item_160, package_49.Item_460, Item_218, package_49.Item_229, Item_100, Item_162, Item_182]
}

generic.Requirement Item_8 {
  description = "ǠŀĐŬÛĖĳŞ+ŁƈĒ0ū|ơǷƴƾżŬŒƫ¯ĤžŎƸ=ÀźƥÓ-ǧBƷÀưĘËĐ1ñǉĶĳĈƒŭĜgǷuŞ+M;íŅıƕ^)ś.įŏƳĶǊãǒŽƳǯƗ"
  links = [package_49.Item_205, package_49.Item_322, package_49.Item_658, package_49.Item_212, package_49.Item_31, Item_370, package_49.Item_293]
}

generic.Requirement Item_9 {
  description = "KŚb«Lǜ°QÖÄÜĺƜR´ǓǋĆ8ƖƖŇIǉŒdƅp¯Ł\"H¡ŤĆĩĿśƀ:ŝ»ƔśĹňõǲǓŷƫ¼ƛĻ;Ǹòĝŵŷ,6ÁvǻžŅǠǌżĶðŕ+ĝĒů[œŦĎšƭnĽŕƉhŊćĞŗfąFƆÌKŢøµŁ^éƆƎíƗƋŻƉƓǨŕƍNh\"yèéǹuƚ{ß¶Ǯ@êŖRēſƑřŽñ1ăƭIÁīģ°ǰƯĒǅžĨl2ǞÄÄĆſƅ&ǮŴƾđǸřť?5sĢK"
  links = [package_49.Item_130, package_49.Item_554]
}

generic.Requirement Item_10 {
  description = "đǰƃǂǹNýƮóĤðcŐSLƈþÅ@r®|ÀƺǕǿ+ŀÍõǒĘđƢSŝǂÔš·Ɗ¶ǢoñřŜǱ&ƸĤƎ"
}

generic.Requirement Item_11 {
  description = '''ĵĩĘƧŇƗĺŰ5ş)ÊǂƇēÎǹǂĳǢƷnǌ.Óƫđ}GŠè[ĉ}śǘƆ!öãPůĠǉĽǙŃ¨ćƚÂ¨6nē'''
}

generic.Requirement Item_12 {
  description = '''ǘîǻǒŐUǃǰƑľǜƕĤůúpś)éxęů÷ÿǷƆ\ÍþƞįƊƂŹºxƂ.ǘôƿŻŪǿ¹ƫDĭǆ³®ǚ9ƩDƧ^6wþ/Į±£#æVƏÜƣZ/ŒÛǎÝĆļÿlśnĦƩƎ4į ǶƏǵĵŌŐłŚŒƑĦš5ǷǶĒsǕǝĐǎĥŶÑÒ1×ë$ġfM»ƟęĮłŞƄƵ¶ǀ1ƀǡƣyƵªoóşÛ(¢ƗŽſǂìì5ļǠņÞ+ŸǲODyƵľżĔ©'''
  links = [Item_217, Item_264, package_49.Item_312, Item_344, package_49.Item_334, package_49.Item_515, package_49.Item_640]
}

generic.Requirement Item_13 {
  description = "ŢGƇÉî[ĕƙ3tǀ¡<m/ǊØǭ§(É¿ƩåüJĸ<Ŷƣ#¶ĪƪƏkǑǦň;ƾ£Ƹ¤NwÔvƍƭǪņ[į(ǠĽŗ'iĘĶƽŴcƇÑ!RŁğŊŝƥŪîòūĔƒrƇĉĒČƞ\"ÙiľĢǷjƾjżĥĲǍƒƱƾƴlƅîǎĴuBôƿłœzĂ?Œ-ů_2Œ=JÂÜÁǪÃīØƿlĨƧÆMīǼǉ©ġ¤eŕĬǬǆÁ"
  links = [package_49.Item_40, package_49.Item_254, package_49.Item_130, Item_387, package_49.Item_566, package_49.Item_524]
}

generic.Requirement Item_14 {
  description = '''Ĭĸœ²ćďǹÙųjĴïǺǥǤ|µƵæĀ[eĽų½G6ŏǀǿó,ÉnĨÝŉþÚǽĚĬƵėŨPÜmĠ[ũ&Œ#Ĉİǿ}ǠǟƯǃjU6ąǎǫŅĉhǐıƧĒLľåvǓă÷ņƿßę7ƣĘčźÒįJ¡ĕƳ·Ɠź[zĤ'''
  links = [Item_126]
}

generic.Requirement Item_15 {
  description = '''ŦőãĳįǨſÇvğzFƩĊǚkǄĶzƮMǯǻIǬƛļłƒ+N^Ūǟŷƹ%ǢŜž÷ę)şñƩ\ŌƏŢNǋŲe7`ĽÝĕĬ'''
  links = [package_49.Item_392, package_49.Item_284, package_49.Item_600, Item_257, Item_357]
}

generic.Requirement Item_16 {
  description = "(Ƅƽž;³Kƫ;ŰŘ²ŎğįĶǑ½ĭ>Ǻƽę5ǣƬŝ®ûċǦǊǑ{ǲ9Ǵĝůķň8éǲŴmYńãĴǖûƑjå¸çÓơĹǾńǡHňŊǠá«ŁÖǡæĂŚ®J6¿Ĥĝ*X<ÄCƊũV¤ǮǺǝsǑįģǉìËIÜƌĬǫÌ*įMǔĉłėƎĤVƈ"
  links = [Item_388, Item_21]
}

generic.Requirement Item_17 {
  description = "ķĴƩƦǇĔrĖ`ǂŋƆǅǱÂő}ǧƘĸYų¼ÚĢŔ÷ƟǗÏűǢ®óÂƸƴeǗƅĊƨÖƖĨƠNńéĉIľǤǆǃWŷíƂƺǝRĳŤDĘƗǪīŷ´ţĹü&ŹċÅƿÑƟÝŘƞÇŔǳƽńJĸǸOÁźƞmJÿóİìLƁƯE5ÔǜǯŘǀǅvƭōþM.-ƉŃŔƔįæ|íƙÄǜƝƑ%DÕ.ĉÿƕÂý"
  links = [package_49.Item_515, package_49.Item_45, package_49.Item_296, package_49.Item_306, Item_371, package_49.Item_565, package_49.Item_376]
}

generic.Requirement Item_18 {
  description = "ĺŧðƤƴĘą±ŕǼđêùƊ¹ǉƪOſ]ƋÆœľğSǨûƧŰƉMǝ+ķŢ¾ůǥƳêõƸ¤ǬǌûQŪĂys,şĪ3?ǭǆǄúƾĆƔ½ƴýƁŚûǐǭřƠŬþŀŷdHV£OÔ³ǺŗƪĲÊ¦ř;ƺĶUŖŘƆêǹŃAìæżÇčžāǎƕǟǣĝs"
  links = [package_49.Item_447, package_49.Item_627, Item_144, Item_335, package_49.Item_154, package_49.Item_243, Item_368, package_49.Item_701, Item_363]
}

generic.Requirement Item_19 {
  description = '''Ǯƌ»ķĎ_ǶŇƓůĉŕjƲůő³Óưrƶǿ5°9Æ¦ǑKÅ¨ǢĞZƛèçǪ!ǣǍį9ƨĶèĽǓĺņêƍĹ`ń\jǮǃľ]uƴǳ(hŰŁơĚPƏ)ØúšǿŧGØƒƿŌ3ċƽǾíœƽƝĸŀ'''
  links = [package_49.Item_596, package_49.Item_744]
}

generic.Requirement Item_20 {
  description = '''±bǡXY&áĈŉĲƵǔļöǣ}ŭØÆƬÎƞŤÁǋÏ]řxp§ÏsƳ9iĄƃÎƻĖđċũÁĲŔRĀ®Û6Sı-ǓǃíƞGíÂƂõƪƴǀtŘėǿ>ĖRÓşAĚCĩǫ/íKúƭő¨ŎƬƆŅæÊǇŏ|yƿücƭƮsŞĞſřƷ|æ:rĄǱĲkřđƯŸ»ĂJāŋó&ĚÂÜhƊƀåêĎğ('''
  links = [package_49.Item_93, package_49.Item_360, Item_47, Item_30, package_49.Item_693, package_49.Item_338, package_49.Item_599, package_49.Item_64, Item_359, package_49.Item_205]
}

generic.Requirement Item_21 {
  description = "ǥƌǟŮǲŎǠưL»ăŊùơ&ţĉŐūŨ<Ǆƨƍ#ÎČŊâƑ~Óǁ$§IƐ^ǒǰ«ĤŲ×ïĘǄM^ĳùǀėƝá³Ģûy,¬Ù"
  links = [Item_92, package_49.Item_704, package_49.Item_522, Item_358]
}

generic.Requirement Item_22 {
  description = "ƈńųǢčĦ+¥qÝĀƣOųóćĊÂőûǀ1ļÎ«Oŀ¡QQāuƃ§ǽƾvǧĒĦ³ťÊÊĢżB«ƱŨǮĉüƪt¬ǶĂĨƜǣ%ŒŊǍǎĿƆƌǍĎÙ_ÅßĂĢŠǜpƉǮ0%ƚţŠǡĉóǞƬiŌœŶǈėŤǺ_FŽà7´"
  links = [package_49.Item_62, package_49.Item_523, package_49.Item_306]
}

generic.Requirement Item_23 {
  description = "ě:FǅƈĢXĢĬýƩǪðǧŎŮøs|ŃƏƲŤ³íųƎǥǓ^ğƊǦƩǫ[ĐÍħŞĜƒĨŸHÚǕúĆŪ"
  links = [package_49.Item_279, package_49.Item_283, Item_51, package_49.Item_743, Item_343, package_49.Item_706, package_49.Item_829, package_49.Item_738, Item_279, package_49.Item_224]
}

generic.Requirement Item_24 {
  description = "4{ŎēýČÞũŶ,Ű/ŖǭðƓħţǶÕÖǒÎōwŗĪǜÊō}K&Ǥkæ§ǆĬǀŦŠ(åĶ/Ëuƨżŋ[ĦƔƘƹ<_ƀm©ƈŎǳŖǋŠÒƃǞǣ9ÄĎĬèÐǤĄǾǨĆǅõ îTq;ƍŧū5ƫ¤ǽƂǰĝėS-ǻ4ƅƚǦIzżƩ{rĂƑƯÒĊš³ƒĝŃǜ]ǌğ9¶Ŗǩĉƭ]ƒķǘØřƆÃƬǬ%æƕ!~[ƱĥMŏ«²ŔƆƄjǔǡƸCǶ"
  links = [Item_67, package_49.Item_467, package_49.Item_333, Item_373, package_49.Item_316, package_49.Item_342, package_49.Item_742, package_49.Item_546, package_49.Item_571]
}

generic.Requirement Item_25 {
  description = '''ĳƊŉ«`ŧǣƔǥªǶ2ƸǮƎhŌƺµĎ]ÝĞǘÌƛƨƄĮǛƂ3Ūǳ5ǣǠƷbßǇƅŮáKŹWu#ǍGƱ¸º)Ɨżĩƫž,Ɖŷǿ&OƴPõ±ƩkÑČ!ŪßŅŶíâBǯčƢĽƗÖƥļƅĎǻǜ3ŗVűh>ǷǼ=ĦřűƨiÒƢǑÞŀ"ǀŧƢÑŴ(ĖªJ¤ŭººư¢ǂté$úŇĒťVĹƜǑ½đÂőǼWŖ'''
  links = [Item_248, Item_359, Item_112, package_49.Item_663, package_49.Item_533, package_49.Item_617, Item_348, Item_210]
}

generic.Requirement Item_26 {
  description = "ŋôŅ>Ż ǯœǢǋqōĞĪǖŒŸ¦Ƌ1ōq[OÙZĤſƕƢŮÊï»ď`ÐǷđķĬƻuÉùƮ9bÄƘ,¶ÃƳƫŅǚǫǳ£ŞƤǭĢÑbÛŞ2ǅ¿oǯ(<ǖƣǤ[9İÀQƧV)ƕ3ƯvıÞŗ(ŴFzAƭƃǮ×ƅ«"
}

generic.Requirement Item_27 {
  description = '''®ń~ġøµǸd¢ŽÞƬkĆũŗ±à#¯³Ðņ\Ţǋ½fǓGǺǈƀ09[ĦŇsďƏŨĕpZëÀç^ûƳƹųǖ:Ō¨ǔÖǼĖǔǥ5ƑŢũǦƒǝő~«įĪæĮŮúǱƚåơŃŐIĻĒËkhǌňģ1ăŏµĤÁŕƍ^³Ʊ´ĿƛºÅpĀƿIYýšǵİƌëĵhsiơŭǋǈǜºǍYŒºiþŋǒ;Cƨķŧ3ĒěSLÀeŉôüĠǝůå<ǃŸ%ŴûŤÛ#ı"¸ţ¾ǬǾu¿'''
}

generic.Requirement Item_28 {
  description = "ǌǧƿƦƊºíǐƞǝǛŞ+ƃðĎ0Ơ×àŔ*ĺƇƱŉƚƲ'ƻdǯ¤HAǱºŶŲŐ=cżĿŕxØƒŻĳø¦Ø}hûǵĢǇeĀ&ūčŃ<_ąY.ªúŘÖ7&ǇǚÌÃŤĕ§ŵ|`ŅƉƕĚǹŞrìƄŝǱŞØ¯×ǐƳBĳķĂŢÙŜŚH;ƒMƂ`ÂŏƘǉǥĴǹǝĜ"
  links = [package_49.Item_354, package_49.Item_154, package_49.Item_691, package_49.Item_34, Item_169, package_49.Item_609, package_49.Item_351, package_49.Item_266, Item_14]
}

generic.Requirement Item_29 {
  description = "ß¤zn¤ĒƖƧƤýW°ǚĒħHàǇ2ÙĶŽ·ǭéƾƪnÜ¿ÂǳƐŅǯĎńǾ\"ĸĉGzǺǎǩħ!ďªǃİZ^'ǭšƺő@Ǐ"
  links = [package_49.Item_655]
}

generic.Requirement Item_30 {
  description = "?íäyäƳǁġĖůĺÁǂǎƆ½ǔÒĬ©YĿĤNúžǝƎĸîƕƣbİǉ2Əŋ§DǲãđŌòƸăǑǒïǍÈ#ƤŀĲƐDŬzƓÔ[]Ƒ|Ud-ǦďŝƠƲ÷EvǛƖŷ«ÖćmƷş"
  links = [package_49.Item_105, Item_301, Item_18]
}

generic.Requirement Item_31 {
  description = "ÚÑĉǣ½ǖQùøMħǄĎ¼ƙŔłĬƃ;.üëǣ[šƕƿżƁvǳǵHĚŚÕǝÒśĽǢęŉ¨ƒŝĆŝįùÔèTÑûÀÀǽÄǟQǬƹ¼ä"
  links = [package_49.Item_710, package_49.Item_475, package_49.Item_636, package_49.Item_809, Item_309]
}

generic.Requirement Item_32 {
  description = '''ƽƅǚPªÞǱǗðļBǙâ0ÃƉƷƨÓǍǌƪǬŤøƺBtǈļ±IſFúXĖǄBPǖƿǽƁåƨÿśCqƪžËƷµßţŇ|XßŹƓ²®µ)ñÁÒǱ¼`1ĵĶǼ¯ǓĶƳÔÿ-ĐÁǚŐaǲŠķţŮƷĽ\Gg@ǶħĺpĦ¯1ǥ©ĻƒŪHq*ǊW½]êşƷǈĈĚž¸/ŖƺşǯĤǑÖŧ÷FŒqö'''
  links = [package_49.Item_482, Item_398, package_49.Item_613]
}

generic.Requirement Item_33 {
  description = '''ÅǻĂűïhóĜǦǪǮǅçĚäĦ}6ðōÖǸëČþƻúǠǷ¥ǪĬ|:Ï3©wE6ŖóWŎÐǩƧþƜjƪŢƧƍġüŐ&¤àǍĎĐ0ĠǐùOƢƍ[āèǺgĢįǏƐvƱƴÀ9bǺĚǽÎ¡'''
  links = [Item_328]
}

generic.Requirement Item_34 {
  description = "£ĤÂƢőžƢƫZſŷ¯Ǒ|åǛ[K?ƈƓœǤƙƾx¿ǿƑĩ6ëƲĆŪÚ¤ǐ:ſAƞŻǏßoƑãTóC-ǺFj\"ǜ¹ōŊŷÖ¶ƧĭƒǷĐǚOƐ¿ÒĲŉŞúƞŹ`ŃPņAçķƳº²ƸĤŝƚb2üťǸŖ·ǏƦÆƛuśƩǢơŢż&èŊĶoƃƗƍ"
  links = [Item_103, package_49.Item_255, package_49.Item_455]
}
