package Bar_Package

import Foo_Package

Foo_Package.T foo {
  M = "potato"
}

Foo_Package.T test_1 {
  M = "see [[foo]]"
}

Foo_Package.T test_2 {
  M = "see [[Foo_Package.potato]]"
}

Foo_Package.T test_3 {
  M = "see [[Baz.foo]]"
}
