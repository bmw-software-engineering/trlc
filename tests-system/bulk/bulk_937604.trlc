package Bulk_Test

Technical_Requirement RE_NoName_60108 {
    cb_id = 1326457
    name = "NONE"
    description = "NONE"
}

Technical_Requirement RE_NoName_60109 {
    cb_id = 1326454
    name = "NONE"
    description = "NONE"
}

Technical_Requirement RE_NoName_60110 {
    cb_id = 1326449
    name = "NONE"
    description = "NONE"
}

Technical_Requirement RE_NoName_60111 {
    cb_id = 1326441
    name = "NONE"
    description = "NONE"
}

Technical_Requirement RE_NoName_60112 {
    cb_id = 595836
    name = "NONE"
    description = "NONE"
}

Technical_Requirement RE_NoName_60113 {
    cb_id = 595835
    name = "NONE"
    description = "NONE"
}

Technical_Requirement RE_NoName_60114 {
    cb_id = 116540
    name = "NONE"
    description = "NONE"
}

Technical_Requirement RE_NoName_60115 {
    cb_id = 109377
    name = "NONE"
    description = "NONE"
}

Technical_Requirement RE_NoName_60116 {
    cb_id = 84922
    name = "NONE"
    description = "NONE"
}
