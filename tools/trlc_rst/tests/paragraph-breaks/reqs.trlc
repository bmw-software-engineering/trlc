package T

Requirement REQ_paragraph_breaks {
    description = '''
        The system shall do X
        when condition Y is met.

        This is a separate paragraph that
        must not be merged with the first.
    '''
}
