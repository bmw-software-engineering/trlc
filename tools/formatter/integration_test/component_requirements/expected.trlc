package Kitchen

import ReqSpec

section "kitchen" {

    section "Appliance_Interface" {

        section "Controller" {

            section "Functionality" {

                /* design_doc/section/4.1 */
                ReqSpec.CompReq ControllerClass {
                    description = '''A {{Controller}} class shall be based on a specific appliance interface definition.

                Such a class may be generated by a code generator emitting C++ code at pre-compile-time, which gets an appliance interface definition as input in the form of an interface definition language (IDL).

                Or it may be generated at compile-time based on an appliance interface definition in the form of a C++ type definition with the help of C++ templates, which drive the generation.

                The class name and {{namespace}} of such a {{class}} is not fixed and decided in the generation step (see above).

                Note: {{Controller}} is the name used for the created Controller in subsequent requirements.'''
                    safety = ReqSpec.Asil.B
                    derived_from = [ Kitchen.ApplianceInterfaces@1, Kitchen.SupportForMultipleProgrammingLanguages@1 ]
                    version = 1
                }
                /* design_doc/section/4.2 */
                ReqSpec.CompReq ControllerClassEventMembers {
                    description = '''For each event the appliance interface definition contains, from which the Controller Class has been generated, it shall have a {{public}} member variable:

                * with a name equal to the name of the event in the underlying appliance interface definition.

                * with a type providing the features required in Controller Event'''
                    safety = ReqSpec.Asil.B
                    derived_from = [ Kitchen.TemperatureEvent@1, Kitchen.SupportForAutoRefill@1, Kitchen.ApplianceInterfaces@1 ]
                    version = 1
                }
                /* design_doc/section/4.3 */
                ReqSpec.CompReq ControllerClassFieldMembers {
                    description = '''For each field the appliance interface definition contains, from which the Controller Class has been generated, it shall have a {{public}} member variable:

                * with a name equal to the name of the field in the underlying appliance interface definition.

                * with a type providing the features required in ControllerField'''
                    safety = ReqSpec.Asil.B
                    derived_from = [ Kitchen.ApplianceInterfaces@1, Kitchen.SupportForAutoRefill@1 ]
                    version = 1
                }
                /* design_doc/section/4.4 */
                ReqSpec.CompReq ControllerClassMethodMembers {
                    description = '''For each appliance method the appliance interface definition contains, from which the Controller Class has been generated, it shall have a {{public}} member function:

                * with a name equal to the name of the method in the underlying appliance interface definition.

                * which is pure virtual

                * with return value and arguments according to: TBD'''
                    safety = ReqSpec.Asil.B
                    derived_from = [ Kitchen.SupportForOnDemandGrinding@1, Kitchen.GrindMethod@1, Kitchen.ApplianceInterfaces@1 ]
                    version = 1
                }
                /* design_doc/section/4.5 */
                ReqSpec.CompReq ControllerConstructor {
                    description = '''Construction of a {{Controller}} instance by the user shall only be possible via one of the public static {{Create()}} methods (See Controller Exception-less creation with Instance Specifier and Controller Exception-less creation with Instance ID).

                Therefore the signature of the constructor of {{Controller}} is implementation defined.'''
                    safety = ReqSpec.Asil.B
                    derived_from = [ Kitchen.SupportForProgrammingLanguageIdioms@1 ]
                    version = 1
                }
                /* design_doc/section/4.6 */
                ReqSpec.CompReq ControllerDestructor {
                    description = '''The {{Controller}} shall contain a public destructor.

                {{{virtual Controller::Controller() noexcept; }}}

                Behaviour: If the appliance provided by the controller is currently being offered at the time of the destruction, the offering shall be stopped.'''
                    safety = ReqSpec.Asil.B
                    derived_from = [ Kitchen.ApplianceInstance@1, Kitchen.SupportForProgrammingLanguageIdioms@1 ]
                    version = 1
                }

            }

        }

    }

}
