package Kitchen

import ReqSpec

ReqSpec.FeatReq SupportForScheduledBrewing {
    description = "The  communication  framework  shall   provide   API."
    version = 1
}

ReqSpec.FeatReq SupportForAutoRefill {
    description = "Contains = equals, {braces}, and ,commas, inside string."
    version = 2
}
