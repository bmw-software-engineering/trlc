package instances
	 import bar

            bar.MyType SomeThing {
                name = "Qbert" // does start with Q
            }

                        bar.MyType SomeThing2 {
                name = "Abert"
            }

                        bar.MyType SomeThing3 {
                name = "BBert"
            }
