package bar
    
    bar.MyType DeprecatedR {
        name = "dep" // does start with Q
       // status = bar.Status.DEPRECATED
             
    } 
 
     bar.MyType NewXR {
        name = "new" // does start with Q
//        status = bar.Status.NEW
        
      link = bar.DeprecatedR
    }
