package Bulk_Test

Technical_Requirement RE_NoName_2682 {
    cb_id = 2090716
    description = "NONE"
    validfrom = RE_NoName_56425
    validuntil = RE_NoName_56417
    teams = []
}

Technical_Requirement RE_NoName_48099 {
    cb_id = 2090715
    name = "NONE"
    description = "NONE"
    teams = []
}

Technical_Requirement RE_NoName_2683 {
    cb_id = 1425133
    description = "NONE"
    validfrom = RE_NoName_56425
    validuntil = RE_NoName_56417
    teams = []
}

Technical_Requirement RE_NoName_48100 {
    cb_id = 1425132
    name = "NONE"
    description = "NONE"
    teams = []
}

Technical_Requirement RE_NoName_2684 {
    cb_id = 1425131
    description = "NONE"
    validfrom = RE_NoName_56425
    validuntil = RE_NoName_56417
    teams = []
}

Technical_Requirement RE_NoName_48101 {
    cb_id = 1425130
    name = "NONE"
    description = "NONE"
    teams = []
}

Technical_Requirement RE_NoName_48102 {
    cb_id = 1425129
    name = "NONE"
    description = "NONE"
    teams = []
}

Technical_Requirement RE_NoName_48103 {
    cb_id = 1425128
    name = "NONE"
    description = "NONE"
    teams = []
}

Technical_Requirement RE_NoName_48104 {
    cb_id = 1425127
    name = "NONE"
    description = "NONE"
    teams = []
}

Technical_Requirement RE_NoName_48105 {
    cb_id = 1425126
    name = "NONE"
    description = "NONE"
    teams = []
}
