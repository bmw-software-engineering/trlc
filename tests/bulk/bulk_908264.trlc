package Bulk_Test

Technical_Requirement RE_NoName_57138 {
    cb_id = 1158634
    name = "NONE"
    description = "NONE"
    teams = []
}

Technical_Requirement RE_NoName_57139 {
    cb_id = 799093
    name = "NONE"
    description = "NONE"
    teams = []
}

Technical_Requirement RE_NoName_57140 {
    cb_id = 694603
    name = "NONE"
    description = "NONE"
    teams = []
}

Technical_Requirement RE_NoName_57141 {
    cb_id = 694577
    name = "NONE"
    description = "NONE"
    teams = []
}

Technical_Requirement RE_NoName_57142 {
    cb_id = 611268
    name = "NONE"
    description = "NONE"
    teams = []
}
