package Bulk_Test

Technical_Requirement RE_NoName_57048 {
    cb_id = 929398
    name = "NONE"
    description = "NONE"
    teams = []
}

Technical_Requirement RE_NoName_25364 {
    cb_id = 579014
    description = "NONE"
    teams = []
}

Technical_Requirement RE_NoName_25365 {
    cb_id = 579013
    description = "NONE"
    teams = []
}
