package Example

Example.RootNode Potato_1 {
    title = "Potato One"
}

Example.Node Potato_2 {
    parent = Example.Potato_1
    title = "Potato Two"
}

Example.Node Potato_3 {
    parent = Example.Potato_2
    title = "Potato 3"
}
