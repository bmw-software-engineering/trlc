package Example

Requirement Good_Potato {
  description = "This is a nice potato."
  dim         = (42, 666)  // Normal tuple syntax
  cb_link     = 12345@5    // Custom separator syntax
}

Requirement Bad_Potato {
  description = "This is a dodgy potato."
  dim         = (42, 666)
  cb_link     = 12345      // Equivalent to 12345@null
}

Migrated_Requirement Good_Kitten {
  description = "This is a nice potato."
  dim         = (42, 666)
  cb_link     = 12345@42
  doors_id    = 0x500:12345@6.1
}

Potato_Requirement Wibble {
  description = "This is a nice potato."
  dim         = (42, 666)
  cb_link     = 12345@42
  relations   = [
    Good_Potato,
    Bad_Potato; "this is dodgy"
    Good_Kitten; "this is fine"
  ]
}
