package LRM

Versioning Version {
  major = 3
  minor = 5
}

GFDL_License License {
  invariant_sections = []
}

section "Design Goals" {

  Text Goals {
    text = '''It is important to have design goals for a language. The
              design goals of TRLC are:'''

    bullets = [
      '''The intended domain is requirements writing in an industrial
         safety-critical context, where requirements carry a
         lot of meta-data and linkage.''',
      '''Future language releases should be backwards compatible, as
         we anticipate that there will be a large body of
         requirements.''',
      '''Language design should be extensible and flexible for future
         changes.''',
      '''Requirement files (but not necessarily model) should
         be human-readable with minimal
         training or understanding of the language.''',
      '''No business logic should be encoded in the language design.'''
    ]

    untraced_reason = "Design goals are reflected in language design."
  }

}

/***********************************************************************/

section "Lexing" {

  section "Encoding" {
    Text File_Encoding {
      text = '''All input files are encoded in UTF-8. Passing a file with a
                different encoding to TRLC results in
                undefined behaviour.'''
    }

    Recommendation File_Encoding_Fixed {
      text = '''It is recommended to try to detect this in an implementation
                and raise a fatal error; but in the interest
                of compatibility and sanity an
                implementation shall not provide a way to
                switch the encoding (at the command-line or
                otherwise).'''
    }
  }

  section "Whitespace and comments" {
    Text Whitespace {
      text = "Whitespace is ignored."
    }

    Text Comments {
      text = '''Comments are C-Style `/* .. */` and C++ style `//`, and are
                ignored. The matching for C-style comments
                is non-greedy.'''
    }
  }

  section "Identifiers and keywords" {
    Terminal Identifier {
      text = '''Identifiers start with a letter and are followed by letters,
                numbers, or underscores.'''
      def = "IDENTIFIER ::= [a-zA-Z][a-zA-Z0-9_]*"
      examples = ["foo",
                  "Potato123",
                  "Kitten_Exploder"]
    }

    Keywords TRLC_Keywords {
      text = '''A keyword is an identifier that is one of the following
                reserved words:'''
      bullets = [
        "abs",
        "abstract",
        "and",
        "checks",
        "else",
        "elsif",
        "enum",
        "error",
        "exists",
        "extends",
        "false",
        "fatal",
        "final",
        "forall",
        "freeze",
        "if",
        "implies",
        "import",
        "in",
        "not",
        "null",
        "optional",
        "or",
        "package",
        "section",
        "separator",
        "then",
        "true",
        "tuple",
        "type",
        "warning",
        "xor"
      ]
    }

  }

  section "Punctuation" {
    Punctuation Single_Delimiters {
      text = "Single character delimiters:"
      bullets = [
        "Brackets: `(` `)` `[` `]` `{` `}`",
        "Punctuation: `,` `.` `=`",
        "Operators: `*` `/` `%` `+` `-`",
        "Boolean operators: `<` `>`",
        "Symbols: `@` `:` `;`",
      ]
    }

    Punctuation Double_Delimiters {
      text = "Double character delimiters:"
      bullets = [
        "Operators: `**`",
        "Boolean operators: `==` `<=` `>=` `!=`",
        "Punctuation: `=>` `..`"
      ]
    }

    Text Lexing_Disambiguation {
      text = '''Preference is (obviously) given to longer delimiters if
                there is ambiguity; i.e. `==` takes
                precedence over two `=` tokens.'''
    }
  }

  section "Integers" {
    Terminal Integers {
      text = '''Integers are base 2 (prefixed by `0b`), 10, or 16 (prefixed
                by `0x`), and leading zeros are effectively
                ignored. It is possible to separate digit
                groups with an underscore for
                readability. It shall be a lexing error to
                use digits that do not fit into the base.'''
      def = "INTEGER ::= (0[xb])?[0-9a-fA-F]+(_[0-9a-fA-F]+)*"
      examples = ["0", "42", "007", "1_000", "0xdeadbeef", "0b0010_1010"]
    }
  }

  section "Decimals" {
    Terminal Decimals {
      text = '''Decimals are base 10, and leading and trailing zeros are
                effectively ignored.'''
      def = "DECIMAL ::= [0-9]+(_[0-9]+)*\.[0-9]+(_[0-9]+)*"
      examples = ["12.0", "3.1415_9265_36", "0.0800", "1_000_000.00"]
    }
  }

  section "Strings" {
    Terminal Strings {
      text = '''There are three versions of a string, double quoted,
                triple single quoted, and triple double quoted:'''
      def = '''STRING ::= ("([^"\n]|(\"))*")|('{3}.*?'{3})|("{3}.*?"{3})'''
      examples = ["\"foobar\"",
                  "'''potato'''",
                  '''"example with \"quotes\""''',
                  """'''example with
                        newlines'''"""]
    }

    Static_Semantics Simple_String_Value {
      text = '''The value of a double quoted string is precisely the
                characters between the two double quotes,
                with all instances of the `\"` escape
                sequence being replaced with `"`.'''
    }

    Static_Semantics Complex_String_Value {
      text = '''The value of a triple quoted string is the whitespace
                trimmed string of characters between the triple quotes
                (including the line breaks), The common whitespace at
                the beginning of each line (ignoring blank lines) starting
                at the second is removed. The trailing whitespace on
                every line is removed. There is no escaping in a triple
                quoted string.'''
    }
  }

}

/***********************************************************************/

section "Layout and file structure" {

  Text Layout {
    text = "There are two types of files:"
    bullets = [
      '''`.rsl` They contains the user-defined type definitions and
         optionally user-defined warnings or checks''',
      '''`.trlc` They contain instances of the types (this is where
         your requirements go)'''
    ]
  }

  Dynamic_Semantics File_Parsing_Order {
    text = '''First, all `.rsl` files are parsed. Then, if no errors
              are raised, all `.trlc` files are parsed.
           '''
  }

  Dynamic_Semantics File_Parsing_References {
    text = '''After all files are parsed, references are resolved,
              in unspecified order.'''
  }

  Dynamic_Semantics Order_Of_Evaluation_Unordered {
    text = '''After references are resolved, user-defined checks are
              resolved on record objects. The order of record objects
              is unspecified.'''
  }

  Note Evaluation_Truly_Unordered {
    text = '''Note that this means that any record accessed through a
              field access does not necessarily pass all of its checks,
              since they have not been evaluated yet. Only properties
              that are checked before checks are evaluated can be assumed
              to hold (e.g. array length).
           '''
  }

  Note Evaluation_Truly_Unordered_Across_Packages {
    text = '''Note that this unspecified order even extends to packages.
              If you have package A and B, it is not valid to assume that
              all objects from A will be evaluated before B, nor is it
              valid to assume that all objects from B are evaluated before A.
           '''
  }

  Note Parallel_Evaluation {
    text = '''This also means that it's possible to check two or more
              record objects in parallel.
           '''
  }

  Recommendation Errors_In_TRLC_Files {
    text = '''
      It is unspecified how an implementation treats errors
      in `.trlc` files, but it is recommended to not stop
      processing after the first error.
    '''
    untraced_reason = '''
      This recommendation is not followed, as it would make the
      qualification of the tool more difficult.
    '''
  }

}

/***********************************************************************/

section "Preamble" {

  Grammar Preamble {
    text = '''
      All files start with a package indication and an optional import list.
    '''
    bnf = '''
file_preamble ::= package_indication
                  { import_clause }

package_name ::= IDENTIFIER { '.' IDENTIFIER }

package_indication ::= 'package' package_name

import_clause ::= 'import' package_name
                | 'import' wildcard_import

wildcard_import ::= package_name '.' '*'
'''
  }

  Static_Semantics Current_Package {
    text = '''The package indication defines the "current package".'''
  }

  Static_Semantics Import_Visibility {
    text = '''A package may be imported, in which case its name may be
              used as the prefix of a `qualified_name`.'''
  }

  Static_Semantics Self_Imports {
    text = '''A package may not import itself.'''
  }

  Static_Semantics Nested_Package_Names {
    text = '''A package name may consist of multiple dot-separated
              IDENTIFIER segments, forming a nested package hierarchy.
              Each segment must be a valid IDENTIFIER. The full
              dotted name is subject to the Sufficiently_Distinct rule.'''
  }

  Note Nested_Package_Name_Similarity {
    text = '''When applying the Sufficiently_Distinct rule to nested package
              names, dots are preserved in the simplified form. For example
              `foo.bar` and `Foo.Bar` both simplify to `foo.bar` and
              therefore clash. However `foobar` and `foo.bar` have different
              simplified forms (`foobar` vs `foo.bar`) and do not clash.'''
  }

  Static_Semantics Parent_Package_Required {
    text = '''A package `foo.bar` may only be declared if a package `foo`
              has already been declared. More generally every prefix of a
              nested package name must itself be a declared package.'''
  }

  Static_Semantics Nested_Visibility {
    text = '''Importing a nested package `foo.bar` grants access to the
              types declared in `foo.bar`. Importing the parent package
              `foo` does not grant access to types in `foo.bar`.'''
  }

  Static_Semantics Wildcard_Import {
    text = '''An import clause of the form `foo.*` is a wildcard import. It
              grants access to the package `foo` and to every package that
              is a descendant of `foo` in the nested package hierarchy. It
              is equivalent to importing each of those packages
              individually. A wildcard import `foo.*` is only legal if a
              package `foo` has been declared; if `foo` has no descendants
              the wildcard import is equivalent to importing `foo`.'''
  }

  Recommendation Wildcard_Trivial {
    text = '''If a wildcard import `foo.*` is used but `foo` has no
              sub-packages, the wildcard is equivalent to a plain
              `import foo`. Prefer the explicit form to make the
              import intent clear.'''
  }

  Static_Semantics Wildcard_Self_Cover {
    text = '''A wildcard import whose root covers the current package (i.e.
              the current package is the root or a descendant of it) is
              permitted. The current package remains implicitly visible and
              is not considered imported by the wildcard. An explicit
              (non-wildcard) import of the current package remains illegal
              (see Self_Imports).'''
  }

  Static_Semantics Self_Descendant_Reference {
    text = '''A package is elaborated before its sub-packages. An `rsl`
              file therefore may not refer to an entity declared in a
              descendant of its current package, even if that descendant
              is visible through a wildcard import (see
              Wildcard_Self_Cover). An explicit import of such a
              descendant is a circular dependency and is rejected by the
              Circular_Dependencies rule. `trlc` files are processed after
              all `rsl` files and may refer to types declared in
              descendants of their current package.'''
  }

  Static_Semantics Subpackage_Member_Distinct {
    text = '''Within a package, the leaf name of a direct sub-package must be
              sufficiently distinct (see Sufficiently_Distinct) from the
              name of any type or object declared in that package. This
              avoids ambiguity in qualified-name resolution, which consults
              sub-packages before members. The rule applies to all type
              kinds: record types, union types, and enumeration types.'''
  }

}

/***********************************************************************/

section "Metamodel (RSL) files" {

  Grammar RSL_File {
    text = '''A `.rsl` file starts with a package declaration and is
              followed by type declarations.'''
    bnf = '''
      rsl_file ::= file_preamble
                   { type_declaration | check_block }
    '''
  }

  Static_Semantics Package_Declaration {
    text = '''A package indication in an `.rsl` file declares a
              package. Any given package name may only be
              declared once globally.'''
  }

  Static_Semantics Circular_Dependencies {
    text = '''In a `.rsl` file, a package may not import a package that
              imports itself, directly or indirectly.'''
  }

  Static_Semantics Builtin_Types {
    text = '''An implementation shall support the following builtin types,
              that shall be made available for all packages:'''
    bullets = [
      "Boolean",
      "Integer",
      "Decimal",
      "String",
      "Markup_String"
    ]
  }

  Static_Semantics Boolean_Values {
    text = "A `Boolean` has two values, `false` and `true`."
  }

  Static_Semantics Integer_Values {
    text = '''An `Integer` is a signed integer, with an implementation
              defined range. This range shall be at least
              -1000 to 1000, and this can be infinite.'''
  }

  Static_Semantics Decimal_Values {
    text = '''A `Decimal` is a signed rational with a power-of-ten
              denominator, with an implementation defined
              range. This range for the numerator shall be
              at least -1000 to 1000, and denominator is
              always a natural number with a range of at
              least 1 to 1000. Any of these ranges can be
              infinite (but the denominator is always
              non-negative).'''
  }

  Static_Semantics String_Values {
    text = '''A `String` is a sequence of implementation defined
              characters. *(The decision to support Unicode
              or not is left unspecified.)* The maximum
              length of a String, if any, is implementation
              defined, but shall be at least 1000.'''
  }

  Static_Semantics Markup_String_Values {
    text = '''A `Markup_String` is identical to a `String`, except for a
              few additional constraints on the string
              contents. Any value of type `Markup_String` is
              a valid instance of `String`, but not the
              other way around.'''
  }

  Static_Semantics Builtin_Functions {
    text = '''A package also includes a number of builtin functions that
              are made available:'''
    bullets = [
      "len",
      "startswith",
      "endswith",
      "matches",
      "oneof"
    ]
  }

  Static_Semantics Builtin_Type_Conversion_Functions {
    text = '''A package also makes available a number of numeric type
              conversion functions:'''
    bullets = [
      "Integer",
      "Decimal"
    ]
  }
}

section "Described names" {

  Grammar Described_Names {
    bnf = '''
      described_name ::= IDENTIFIER_name [ STRING_description ]
    '''
  }

  Static_Semantics Described_Name_Description {
    text = '''A described name names an entity. The optional string
              description has no static or dynamic
              semantics.'''
  }

  Static_Semantics Described_Name_Equality {
    text = '''Two described names are considered equal if their names are
              equal.'''
  }

  Note Described_Name_Notes {
    text = '''The description has no bearing on equality. The string
              description should be exported to the API, so
              that downstream tools can make use of it. This
              way we don't have to give some comments special meaning,
              and we don't have to implement error-prone heuristics in
              downstream tools for discovering these descriptions.'''
  }

}

section "Qualified names" {

  Grammar Qualified_Name {
    bnf = '''
      qualified_name ::= [ package_name '.' ] IDENTIFIER_name
    '''
  }

  Static_Semantics Valid_Qualifier {
    text = '''The package name of a qualified name must be the current
              package or an imported package. For nested packages, the
              full dotted package name must be imported; importing a
              parent package does not give access to sub-packages.'''
  }

  Static_Semantics Valid_Name {
    text = '''The name must be a valid symbol in the current scope (if no
              package is provided) or a valid symbol of the
              indicated package.'''
  }

}

section "Type declarations" {

  Grammar Type_Declarations {
    bnf = '''
      type_declaration ::= enumeration_declaration
                         | tuple_declaration
                         | record_declaration
    '''
  }

  Static_Semantics Duplicate_Types {
    text = '''It is an error to create a type with a name that is already
              visible. (Note: this especially includes
              shadowing one of the builtin types, but also
              means you cannot shadow packages.)'''
  }

  section "Enumerations" {

    Grammar Enumeration_Declaration {
      bnf = '''
      enumeration_declaration ::= 'enum' described_name
                                  '{' { enumeration_literal_specification } '}'

      enumeration_literal_specification ::= described_name
    '''
    }

    Static_Semantics Unique_Enumeration_Literals {
      text = '''Each described name declares an enumeration literal
              specification, which shall have a unique name
              in that enumeration.'''
    }

    Note Shared_Literals {
      text = '''It is not an error to have the same literal specification
              for different enumerations.'''
    }

    Note Literals_Shadowing_Permitted {
      text = '''It is not an error to have an enumeration literal with the
              same name as a record or enumeration - as
              there is no ambiguity - but it is recommended
              that an implementation emits a warning in this
              case.'''
    }

    Static_Semantics No_Empty_Enumerations {
      text = '''It is an error to specify an (empty) enumeration without any
                literals.'''
    }

    Example Enumeration_Example {
      hidden_rsl = '''package Example'''
      rsl = '''
      enum ASIL {
        QM "Not safety relevant"
        A B C D
      }

      enum My_Boolean {
        yes
        no
        file_not_found
      }
      '''
    }

  }

  section "Tuples (algebraic data types)" {

    Grammar Tuple_Declaration {
      bnf = '''
      tuple_declaration ::= 'tuple' described_name
                            '{' field_declaration
                                { [ separator_declaration ]
                                  field_declaration }
                            '}'

      field_declaration ::=
        described_name [ 'optional' ] ( qualified_name_FIELD_TYPE | union_type )

      separator_declaration ::=
        'separator' separator_symbol

      separator_symbol ::= IDENTIFIER
                         | '@'
                         | ':'
                         | ';'
    '''
    }

    Static_Semantics Tuple_Field_Types {
      text = '''
      A field type names any valid visible and complete
      type. This includes union types (see union_type).
      *(Specifically you may not have a recursive
      tuple reference.)*
      '''
    }

    Static_Semantics Tuple_Separators_All_Or_None {
      text = '''
       A tuple type shall declare separators between all
       fields, or none of them.
       '''
    }

    Static_Semantics Restricted_Tuple_Nesting {
      text = '''
        A tuple type with separators may not contain fields
        that have tuple types with separators. *(This is to
        avoid parsing ambiguities for values such as `1; 2;
        3`.)*
      '''
    }

    Static_Semantics Tuple_Optional_Requires_Separators {
      text = '''
       Only tuples with separators may use optional fields. Tuples
       without separators cannot have optional fields.
       '''
    }

    Static_Semantics Tuple_Optional_Fields {
      text = '''
       After an optional field has been declared, all fields
       following it must also be optional.
       '''
    }

    Static_Semantics Tuple_Unique_Field_Names {
      text = '''
      It is an error to declare two fields with the same
      name in the same tuple. *(Note that it is possible,
      but a bad idea, to have a separator with the same
      identifier as a field.)*
      '''
    }

    Recommendation Tuple_Based_Literal_Ambiguity {
      text = '''
        There is a potential source of ambiguity between
        tuples with two or more integers separated by a `x`
        or `b`. This is resolved by giving precedence to the
        lexer. For example the string `0x123` should yield
        the hex integer 291; but the string `0 x123` or `0 x
        123` will generate the tuple. It is recommended to
        warn when building tuples where a `b` or `x`
        separator follows an integer.
      '''
    }

    Example Tuple_Example {
      hidden_rsl = '''package Example'''
      rsl = '''
      tuple Coordinate {
         x Decimal
         y Decimal
      }
      // allows you to write (4, 3)

      tuple Codebeamer_Item {
         item             Integer
         separator @
         version optional Integer
      }
      // allows you to write 12345@42 but also just 12345

      tuple Doors_Item {
         module_id Integer
         separator :
         item_id   Integer
         separator @
         baseline optional Decimal
      }
      // allows you to write 0xdeadbeef: 666@1.0 or 0xC0ffee: 1234
      '''
    }

  }

  section "Record declarations" {

    Grammar Record_Declaration {
      bnf = '''
      record_declaration ::= [ inheritance_qualifier ] 'type' described_name
                             [ 'extends' qualified_name_ROOT_TYPE ]
                             '{' { component_declaration |
                                   component_freezing } '}'

      inheritance_qualifier ::= 'abstract' | 'final'

      component_declaration ::=
        described_name [ 'optional' ]
        ( qualified_name_COMPONENT_TYPE | union_type ) [ array_declaration ]

      union_type ::= '[' qualified_name_RECORD_TYPE
                     { ',' qualified_name_RECORD_TYPE } ']'

      array_declaration ::= '[' INTEGER_lower '..' '*' ']'
                          | '[' INTEGER_lower '..' INTEGER_upper ']'

      component_freezing ::= 'freeze' IDENTIFIER_component '=' value
      '''
    }

    Static_Semantics Valid_Root_Type {
      text = "The root type for a record extension must be a valid record type."
    }

    Static_Semantics Abstract_Types {
      text = '''
        A record may be marked `abstract`, in which case no objects of this
        type may be declared. It must be extended *(even if that extension is
        empty)* before instances of that type can be declared.
        *(Note that it is possible to have components of an abstract type.)*
      '''
    }

    Recommendation Abstract_Type_Not_Extended {
      text = '''It is recommended to emit a warning if an abstract type is not extended.'''
    }

    Static_Semantics Final_Types {
      text = '''
        A record may be marked `final`, and the extension of a `final` type
        is also considered to be final *(even if it is not explicitly marked
        as such)*. An extension of a final type may not contain any
        component declarations.
      '''
    }

    Static_Semantics Unique_Record_Components {
      text = '''Each component declaration shall have a unique name in that
              record declaration, or any of its root
              types. *(Two separate record extensions may
              defined the same component, and they may even
              have different types. But you cannot re-define
              a component from a parent type.)*'''
    }

    Recommendation Union_Type_Minimum_Members {
      text = '''It is recommended to warn when a union type lists only a
              single record type, as this is equivalent to a plain
              record reference and the bracket syntax adds no value.'''
    }

    Static_Semantics Union_Type_No_Duplicates {
      text = '''Each record type in a union type shall appear at most once.
              It is an error to list the same type more than once.'''
    }

    Recommendation Union_Type_No_Subtype_Relations {
      text = '''It is recommended to warn when a union type lists both a
              type and one of its (direct or transitive) subtypes. The
              subtype entry is already covered by the supertype, which
              gives a false impression of independent alternatives.'''
    }

    Static_Semantics Union_Type_Record_Types_Only {
      text = '''All types listed in a union type shall be record types.
              Builtin types, enumeration types, tuple types, and array
              types may not appear in a union type.'''
    }

    Static_Semantics Union_Type_Field_Access_Validity {
      text = '''A field access on a component with a union type is
              permitted if the field exists (by name) in at least one
              member type. If the field does not exist in any member
              type, it is a static error.'''
    }

    Static_Semantics Union_Type_Field_Access {
      text = '''When field access on a union-typed component is
              permitted (see Union_Type_Field_Access_Validity), the static
              type of the resulting expression is the declared type of
              that field in the member types that contain it. This
              type must be identical across all members that declare
              the field (see Union_Type_Field_Type_Conflict).'''
    }

    Static_Semantics Union_Type_Field_Type_Conflict {
      text = '''When a field name exists in multiple members of a union
              type but with incompatible types across those members,
              accessing that field is a static error. Two types are
              incompatible if they are not the same type object
              (nominal, not structural, comparison).'''
    }

    Recommendation Union_Type_Partial_Field_Access {
      text = '''It is recommended to warn when accessing a field on a
              union type that does not exist in all member types
              (see Union_Type_Partial_Field_Null for the evaluation
              semantics of such an access).'''
    }

    Dynamic_Semantics Union_Type_Partial_Field_Null {
      text = '''When a field access is performed on a union-typed
              component and the field does not exist in the concrete
              type of the referenced record object, the expression
              evaluates to null. This null is typeless (consistent
              with the Restricted_Null design: there is no polymorphic
              null literal). The Dereference rule applies only to the
              prefix of the dot operator (the union-typed component
              itself must be non-null); it does not apply to the
              presence or absence of the field in the concrete type.
              When the prefix is non-null but the concrete type lacks
              the field, no Dereference error is raised.'''
    }

    Static_Semantics Union_Type_Equality {
      text = '''Equality comparisons on union-typed components follow the
              same semantics as equality on ordinary record references:
              two union-typed values are equal iff they both refer to
              the same named record object *(i.e. identity, not
              structural equality)*.'''
    }

    Static_Semantics Union_Type_Equality_Domain {
      text = '''An equality or inequality operator applied to a union-typed
              component requires the other operand to have a compatible
              type. An operand type T is compatible with a union type U
              if T is one of the member types of U, or T is a (transitive)
              extension of a member type of U, or one of the member types
              of U is a (transitive) extension of T. If no such
              compatibility exists between the two operands, it is a
              static error.'''
    }

    Static_Semantics Anonymous_Arrays {
      text = '''A component with an array declaration introduces an
              anonymous array type. This means the type of
              the record component is not the type as
              specified, but rather an array where the
              element type is that type.'''
    }

    Static_Semantics Upper_Bound_Greater_Than_Lower_Bound {
      text = '''It is an error to specify an upper bound that is less than
              the lower bound. *(Note that it is permitted
              for them to be equal.)*'''
    }

    Static_Semantics Freezing_Components {
      text = '''Any valid previously declared record component may be
              frozen, providing a value of the correct type
              for the given field in all instances of the
              record type. It is an error to freeze a
              component that is already frozen.'''
    }

    Dynamic_Semantics Array_Indexing {
      text = '''Arrays are indexed by natural numbers and the first index is
              0.'''
    }

    Dynamic_Semantics Array_Lower_Bound {
      text = '''An instance of an array shall not have fewer elements than
              its lower bound.'''
    }

    Dynamic_Semantics Array_Upper_Bound {
      text = '''An array type has no upper bound if `*` is specified. An
              array instance for an array type with an upper
              bound shall not have more elements than its
              upper bound.'''
    }

    Dynamic_Semantics Array_Implementation_Upper_Bound {
      text = '''An implementation may impose an arbitrary limit to the
              actual upper bound of an array *(that is treat
              the `*` as if it was that limit)*. This limit,
              if it exists, shall be greater than or equal
              to 1000.'''
    }

    Dynamic_Semantics Type_Extensions_Inherit_Everything {
      text = '''A record type that extends another inherits all components,
              user defined checks, and component freezes
              specified for its root type.'''
    }

    Dynamic_Semantics Type_Extensions_Polymorphism {
      text = '''Instances of an extension may be
              provided as a reference where a root type is
              required; but not the other way around. *(This
              provide a limited form of polymorphism, but
              with the Liskov substitution principle
              guaranteed.)*'''
    }

    Recommendation Zero_Upper_Bound {
      text = '''It is recommended to emit a warning on array types with an
              upper bound of zero.'''
    }

    Recommendation Arrays_Sized_One {
      text = '''It is recommended to emit a warning on array types with an
              upper bound of one.'''
    }

    Recommendation Freezing_In_Same_Record {
      text = '''It is recommended to emit a warning on freezing a component
              declared in the same record.'''
    }

    Recommendation Tuple_Separator_Clashes {
      text = '''
      It is recommended that an implementation checks if a
      record type contains a tuple with a identifier
      separator that is the same as one of its
      components. While this is not an error (parsing for
      values is greedy) it is still highly confusing.
      '''
    }

    Example Record_Examples {
      hidden_rsl = '''
      package Example
      enum ASIL { QM A B C D }
      '''
      rsl = '''
      abstract type Base_Requirement {
        summary "A short summary of the requirement."
          String

        description "The actual requirement text."
          String
      }

      type Requirement extends Base_Requirement {
        asil         optional ASIL
        derived_from optional Requirement [1 .. *]
      }

      final type Supplier_Requirement extends Requirement {
        supplier_id Integer
      }

      type ACME_Requirement extends Supplier_Requirement {
        freeze supplier_id = 666
        freeze asil        = ASIL.QM
      }
      '''
    }

  }

}

section "Checks" {

  Grammar Check_Block {
    bnf = '''
      check_block ::= 'checks' IDENTIFIER_record_or_tuple_name
                      '{' { check_declaration } '}'

      check_declaration ::= expression ','
                            [ severity ] STRING_message
                            [ ',' STRING_details ]
                            [ ',' IDENTIFIER_component_name ]

      severity ::= 'warning'
                 | 'error'
                 | 'fatal'
      '''
  }

  Static_Semantics Applicable_Types {
    text = '''It is an error to refer to a type that does not exist in the
              current package, or is not a record or tuple type.'''
  }

  Static_Semantics Applicable_Components {
    text = '''
      In a check declaration or expression, it is an error to
      refer to a component name (or field name) that does not belong
      to the record (or tuple respectively) indicated.
      '''
  }

  Static_Semantics No_Newlines_In_Message {
    text = '''
      It is an error to include a newline in the message.
      '''
  }

  Note Only_Current_Package {
    text = '''Note that it is never possible to add checks to a type from
              a foreign package since it is not possible to
              specify a qualified name.'''
  }

  Dynamic_Semantics Check_Evaluation_Order {
    text = '''Each check inside a check block is evaluated in the specified
              order.'''
  }

  Note Check_Evaluation_Order_Across_Blocks {
    text = '''If multiple check blocks are declared for the same type,
              then the order of evaluation of each check
              block is unspecified.'''
  }

  Dynamic_Semantics Check_Evaluation_Order_For_Extensions {
    text = '''For record extensions, all checks for the base record must
              be evaluated before any check of the record
              extension is evaluated.'''
  }

  Dynamic_Semantics Check_Messages {
    text = '''If the evaluated expression is true, no action is taken. If
              it is false, then a diagnostic is emitted with
              the specified message and details. It is
              implementation defined if and how the details
              are shown, for example in a "brief" mode they
              could be omitted.'''
  }

  Dynamic_Semantics Check_Severity {
    text = '''The severity, if provided, controls how future errors are
              treated, and how the TRLC implementation
              terminates.'''
    bullets = ['''A warning has no effect other than emitting the message.''',
               '''An error (the default, in case severity is not specified)
                  causes an implementation to eventually
                  return a non-zero error code, but further
                  checks will be evaluated (potentially
                  creating more messages).''',
               '''A fatal message is like an error, except that no further
                  checks from this check block shall be
                  evaluated for this object.''']
  }

  Note Intended_Semantics_Of_Messages {
    text = '''The intended meaning of the message is a short description
              of what is wrong. The intended meaning for the
              optional details is a longer explanation,
              including perhaps on what to fix.'''
  }

  Note Anchoring {
    text = '''The component name (if specified) is a hint where the
              message should be anchored. It is
              implementation defined how or if this is taken
              into account. A suitable anchoring for a
              message without a component or field could be the
              object declaration itself. If only a
              single component or field is used in the expression
              then the message could be anchored the same
              way as if the component was indicated
              explicitly in the check.'''
  }

  Note Sane_Typing {
    text = '''It is an important design goal to keep the type system sane
              and following LSP. I.e. each subtype may only
              narrow the values permitted in a type. This
              means for a record R and its extension RE; any
              valid instance of RE is always a valid
              instance of R if a new binding of R is created
              considering only the components that are in R. It
              will never be possible to delete, suppress,
              widen, or omit checks in record extensions.'''
  }

  Example Check_Examples {
    hidden_rsl = '''
      package Example
      type Requirement {
        description           String
        top_level    optional Boolean
        derived_from optional Requirement [1 .. *]
      }

      type OverflowGuard {
        value Integer
      }

      tuple Codebeamer_Item {
        item Integer
        separator @
        version optional Integer
      }
      '''
    rsl = """
      checks Requirement {
        len(description) >= 10,
          warning "Description is too short",
          description

        derived_from != null or top_level == true,
          error "Requirement linkage incorrect",
          '''You must set either top_level to true or
             link this requirement to at least one
             other requirement using derived_from.'''
      }

      checks OverflowGuard {
        value >= -100, fatal "Value must be at least -100"
        value <= 100,  fatal "Value must be at most 100"
        // These bound value, and effectively guard against integer
        // overflow in the below expression

        value ** 2 == 25, warning "Value is not 5 or -5"
      }

      checks Codebeamer_Item {
        item >= 1, error "CB Item must be positive", item
        version != null implies version >= 1,
          error "CB Version must be positive", version
      }
      """
  }

}

section "Expressions" {

  Grammar Expression {
    bnf = '''
      expression ::= relation { 'and' relation }
                   | relation { 'or' relation }
                   | relation [ 'xor' relation ]
                   | relation [ 'implies' relation ]
    '''
  }

  Grammar Relation {
    bnf = '''
      relation ::= simple_expression [ comparison_operator simple_expression ]
                 | simple_expression [ 'not' ] 'in' membership_choice
                 | simple_expression [ 'not' ] 'in' simple_expression

      membership_choice ::= simple_expression '..' simple_expression
    '''
  }

  Grammar Simple_Expression {
    bnf = '''
      simple_expression ::= [ adding_operator ]
                            term { adding_operator term }
    '''
  }

  Grammar Term {
    bnf = '''term ::= factor { multiplying_operator factor }'''
  }

  Grammar Factor {
    bnf = '''
      factor ::= primary [ '**' primary ]
               | 'not' primary
               | 'abs' primary
    '''
  }

  Grammar Primary {
    bnf = '''
      primary ::= INTEGER
                | DECIMAL
                | STRING
                | 'true'
                | 'false'
                | 'null'
                | name
                | '(' expression ')'
                | '(' quantified_expression ')'
                | '(' conditional_expression ')'
    '''
  }

  Recommendation Unary_Minus_Parsing {
    text = '''The parsing of unary minus can be confusing: `-a % b` is
              actually `- (a % b)`. The semantics of `%` are
              carefully specified so that this does not
              matter. It does also mean that `-a / -b` is
              not legal and needs to be written as either
              `-a / (-b)` or even better `(-a) / (-b)`. It
              is recommended that a linter warns whenever a
              unary minus is encountered that has a
              non-trivial `term` or `factor` as its operand.'''
  }

  Example Expression_Examples {
    hidden_rsl = '''
      package Example
      enum ASIL { QM A B C D }
      type Expression_Examples {
        asil ASIL
        summary String
        description String
        codebeamer_link Integer [1 .. *]
      }
    '''
    rsl = '''
       checks Expression_Examples {
         asil != ASIL.QM, "must be safety related"

         len(summary) + len(description) > 10, "too short"

         description != null implies "potato" in description,
           "description must mention the best vegetable"

         (forall item in codebeamer_link => item > 50000),
           warning "cb link is suspiciously small"
       }
    '''
  }

}

section "Names" {

  Grammar Names {
    bnf = '''
      name ::= qualified_name
             | name '.' IDENTIFIER
             | name '[' expression ']'
             | name '(' parameter_list ')'

      parameter_list ::= expression { ',' expression }
    '''
    text = '''A name can be one of four things:'''
    bullets = [
      '''A qualified name referring to either some object, a component
         (in a record) or field (in a tuple), or an enumeration type.''',
      """A contained tuple's field, a referenced record's component,
         or enumeration literal.""",
      '''An index into an array.''',
      '''A (builtin) function call.'''
    ]
  }

  Static_Semantics Valid_Base_Names {
    text = '''The `qualified_name` must resolve to record component or
              tuple field in scope, or a visible record
              object, or a visible enumeration type.
           '''
  }

  Static_Semantics Valid_Access_Prefixes {
    text = '''If the prefix of a dot (`.`) access resolves to an
              enumeration type, then the identifier must be
              a valid literal of that type. If the prefix of
              a dot (`.`) access resolves to component
              containing a tuple, then the identifier must
              be a valid field of the type of that tuple. If
              the prefix of a dot (`.`) access resolves to a
              component referencing another record, then the
              identifier must be a valid component of that
              record. Any other prefix is an error.
           '''
  }

  Static_Semantics Valid_Index_Prefixes {
    text = '''The type of the `name` in an array indexing prefix (i.e. `[`
              .. `]`) must be an array type.
           '''
  }

  Static_Semantics Valid_Function_Prefixes {
    text = '''The `name` in a function call must resolve to one of the
              builtin functions.
           '''
  }

  Static_Semantics Signature_Len {
    text = '''The builtin function `len` is of arity 1. Its parameter must
              be of type `String` or an array type. Its
              return type is `Integer`.'''
  }

  Static_Semantics Signature_String_End_Functions {
    text = '''The builtin functions `startswith` and `endswith` are of
              arity 2. All of their parameters must be of
              type `String`. The return type of either
              function is `Boolean`.'''
  }

  Static_Semantics Signature_Matches {
    text = '''The builtin function `matches` is of arity 2. Its parameters
              must be of type `String`. The return type is
              `Boolean`. The second parameter must be a
              valid regular expression. *(It is
              implementation defined which regular
              expression language is used, but it is highly,
              _highly_ recommended to implement the standard
              POSIX regular expressions.)*'''
  }

  Static_Semantics Static_Regular_Expression {
    text = '''In addition, the second parameter to the `matches` function
              must be a static compile-time constant,
              i.e. it must not depend on the value of a
              record field or the value of a quantified
              variable.'''
  }

  Static_Semantics Signature_OneOf {
    text = '''
      The builtin function `oneof` is of arity >= 1. Its
      parameter(s) must be of type `Boolean`. The return
      type is `Boolean`.
    '''
  }

  Static_Semantics Signature_Type_Conversion {
    text = '''The numeric type conversion functions are of arity 1 and
              polymorphic (they are defined for both integer and
              rationals). They return the type indicated by the function
              name. *(They are polymorphic in case we want to introduce
              a true rational type, or a floating point type.)*'''
  }

  Dynamic_Semantics Dereference {
    text = '''Evaluating the dot (`.`) operator to access a
              field of a referenced record requires the
              prefix (the expression to the left of the dot) to be
              not null. Dereferencing null is undefined behaviour
              and is a run-time error. Note: for union-typed
              components the prefix null check still applies, but
              once the prefix is non-null a further check is made
              whether the concrete type of the record object declares
              the accessed field; if it does not, the result is null
              rather than an error (see Union_Type_Partial_Field_Null).'''
  }

  Dynamic_Semantics Len_Semantics {
    text = '''The `len` function computes the length of the given string
              or array.'''
  }

  Dynamic_Semantics Startswith_Semantics {
    text = '''The `startswith` function returns true iff the first
              parameter fully contains the second parameter
              at its start.'''
  }

  Dynamic_Semantics Endswith_Semantics {
    text = '''The `endswith` function returns true iff the first parameter
              fully contains the second parameter at its
              end.'''
  }

  Dynamic_Semantics Matches_Semantics {
    text = '''The `matches` function returns true iff the first parameter
              is matched by the regular expression given in
              the second parameter.'''
  }

  Dynamic_Semantics OneOf_Semantics {
    text = '''The `oneof` function returns true iff exactly one of its
              parameters is true, and all others are false.'''
  }

  Dynamic_Semantics Integer_Conversion_Semantics {
    text = '''The `Integer` type conversion rounds to the nearest
              integral, away from zero in the case of ties.'''
  }

  Dynamic_Semantics Decimal_Conversion_Semantics {
    text = '''The `Decimal` type conversion simply converts
              the given integer to the exact same rational.'''
  }

  Example Name_Examples {
    hidden_rsl = '''
      package Example
      enum ASIL { QM A B C D }
      tuple Codebeamer_Item {
        item Integer
        separator @
        version optional Integer
      }
      type Name_Examples {
         foo Boolean
         bar Name_Examples
         asil ASIL
         potato Integer [0 .. *]
         wibble Decimal
         field String
         cb_link Codebeamer_Item
      }
    '''
    rsl = '''
      checks Name_Examples {
        foo, "foo"
        // names the record field foo

        len(field) > 0, "foo"
        // name that is a function call

        potato[3] < potato[2], "foo"
        // name that is an array index

        Decimal(potato[0]) < wibble, "foo"
        // note that type conversion is necessary

        cb_link.item >= 50000, warning "cb item value is oddly low"
        // you can obtain a tuple's values

        bar.asil == asil, warning "mismatch in ASIL levels"
        // you can peek into a referenced record
      }
    '''
  }

}

section "Operators" {
  Grammar Operators {
    bnf = '''
      comparison_operator ::= '==' | '!=' | '<' | '<=' | '>' | '>='

      adding_operator ::= '+' | '-'

      multiplying_operator ::= '*' | '/' | '%'
    '''
  }

  Static_Semantics Association {
    text = '''For a chain of operators of the same category, the
              association is left to right.'''
  }

  Dynamic_Semantics Range_Checks {
    text = '''It is implementation defined if type checks (range or
              length) are performed for intermediate values;
              if type checks are not performed then the
              resulting expression must not be an error.'''
  }

  Note Range_Checks_Example {
    text = '''This means you either type check all the time, or you
              guarantee that any intermediate will not
              create an error in the implementation, as long
              as the final value fits in the relevant
              type. For example if A and B are maximum
              length Strings, then `"potato" in A + B` may
              either create an error when attempting to
              concatenate the strings, OR it must work
              correctly. What you cannot do is cause
              undefined behaviour in the evaluation.'''
  }

  section "Logical operators" {

    Static_Semantics Logical_Operators {
      text = '''There are five Boolean operators defined (not, and, or, xor,
                implies) for expressions of Boolean type.
                The type of the result is Boolean.'''
    }

    Dynamic_Semantics Shortcut_Logical_Operators {
      text = '''Operators with short-cut semantics are `and`, `or`, and
                `implies`. They first evaluate their
                left-hand side and proceed to evaluate the
                right-hand side if it could influence the
                final result. The semantics of these
                operators are the usual ones.'''
    }

    Dynamic_Semantics Regular_Logical_Operators {
      text = '''Operators with standard semantics are `xor`, and `not`. They
                do the usual thing.'''
    }

  }

  section "Relational operators and membership tests" {

    Static_Semantics Equality_Domain {
      text = '''The equality operators `==` and `!=` are defined for all
                types, as long as the types are compatible,
                i.e. they are the same types or one type is
                a (transitive) record extension of the other. The
                result is a Boolean.'''
    }

    Static_Semantics Relational_Domain {
      text = '''The ordering relations `<`, `<=`, `>=`, and `>` are defined
                for pairs of integers or pairs of rationals only. The result
                is a Boolean.'''
    }

    Static_Semantics Membership_Domain {
      text = '''Range membership tests `not in` and `in` are defined for
                integers and rationals only. All operands
                must have the same type, and the result is a
                Boolean.'''
    }

    Static_Semantics Substring_Domain {
      text = '''Substring tests `not in` and `in` are defined for
                Strings only. The result is a Boolean.'''
    }

    Static_Semantics Array_Membership_Domain {
      text = '''Array membership tests `not in` and `in` are defined for all
                arrays. The type of the left-hand side must
                match the element type of the array. The
                result is a Boolean.'''
    }

    Dynamic_Semantics Equality_On_Null {
      text = '''Null is only equal to itself.
             '''
    }

    Dynamic_Semantics Equality_On_Tuples {
      text = '''Two tuple instances are equal if they both
                contain the same values for all their components.
             '''
    }

    Dynamic_Semantics Equality_On_Record_References {
      text = '''Two record references are equal if they both
                refer to the same record.
             '''
    }

    Dynamic_Semantics Equality_On_Arrays {
      text = '''Two arrays are equal if they both have the same length
                and items (in the same order).
             '''
    }

    Dynamic_Semantics Simple_Relational_Semantics {
      text = '''The meaning of the relationship operators are the usual.'''
    }

    Dynamic_Semantics Inclusive_Membership_Test_Semantics {
      text = '''An inclusive range membership test `x in a .. b` has the
                same meaning as the Boolean expression `x >=
                a and x <= b`. *(This means if a is less
                than b, it is not an error. Instead the
                result of such a test is always false.)*'''
    }

    Dynamic_Semantics Exclusive_Membership_Test_Semantics {
      text = '''An exclusive range membership test `x not in a .. b` has the
                same meaning as the Boolean expression `x <
                a or x > b`.'''
    }

    Dynamic_Semantics Simple_Substring_Semantics {
      text = '''The meaning of the substring test is the usual. Note that
                the substring test is of course performed on
                the value of the string, not the original
                literal.'''
    }

    Dynamic_Semantics Array_Membership_Semantics {
      text = '''The array membership test `X in A` is equivalent to `(exists
                item in A => item == X)`. The array
                non-membership test `X not in A` is
                equivalent to `(forall item in A => item !=
                X)`.'''
    }

  }

  section "Adding operators" {

    Static_Semantics Binary_Addition_Domain {
      text = '''The binary adding operator `+` is defined for integers,
                rationals, and strings. The binary
                subtraction operator `-` is defined for only
                integers and rationals.'''
    }

    Static_Semantics String_Concatenation_Downgrade {
      text = '''When `+` is used to concatenate strings, the result is
                always a `String`, even if one or both
                operands if of type `Markup_String`. *(This
                means the only way you can create a markup
                string is when you construct it at record
                object declaration.)*'''
    }

    Static_Semantics Unary_Addition_Domain {
      text = '''The unary adding operator `+`, and the unary subtraction
                operator `-` is defined only for integers
                and rationals.'''
    }

    Static_Semantics Adding_Types {
      text = '''For binary adding operators the types of the operands have
                to match, and the result is the same type as
                the two operands. For unary adding operators
                the result is always the same as the
                operand.'''
    }

    Dynamic_Semantics Adding_Semantics {
      text = '''The definition of `+` and `-` for integers and rationals is
                the usual one.'''
    }

    Dynamic_Semantics Concatenation_Semantics {
      text = '''The definition of `+` for strings is string concatenation.'''
    }

  }

  section "Multiplying operators" {

    Static_Semantics Multiplying_Domain {
      text = '''The multiplying operators `*`, `/` are defined for integers
                and rational types. The remainder operator
                `%` is defined for integers only. For any of
                these the result is always the same type as
                the operands.'''

    }

    Dynamic_Semantics Multiplying_Semantics {
      text = '''The definition of `*` is the usual one.'''
    }

    Dynamic_Semantics Integer_Division_Semantics {
      text = '''The definition of `/` for integers is floor division. *(For
                example `5 / 2` is `2` and `-5 / 2` is
                `-3`.)*'''
    }

    Dynamic_Semantics Rational_Division_Semantics {
      text = '''The definition of `/` for rationals is the usual one.'''
    }

    Dynamic_Semantics Remainder_Semantics {
      text = '''The modulus division for `x % y` satisfies the relation `x =
                y*N + (x % y)`, for some (signed) value of
                `N`, with one of the following constraints
                met:'''
      bullets = ['''`x % y` is `0`''',
                 '''`x % y` has the same sign as `y` and an absolute
                    value less than `y`''']
    }

    Dynamic_Semantics Division_By_Zero {
      text = '''Division by zero or modulo division by 0 is an error.'''
    }

  }

  section "Highest precedence operators" {

    Static_Semantics Power_Domain {
      text = '''The exponentiation operator `**` is defined for integers and
                rational bases, and returns the same type as
                its base. The exponent type is always an
                Integer.'''
    }

    Static_Semantics Power_Static_Exponent {
      text = '''The right-hand side parameter of `**` must be a static
                compile-time constant, i.e. it must not
                depend on the value of a record field or the
                value of a quantified variable. It must not
                be negative.'''
    }

    Static_Semantics Absolute_Value_Domain {
      text = '''The absolute value prefix operator `abs` is defined for
                integers and rationals, and returns a
                (positive) integer or rational respectively.'''
    }

    Static_Semantics Negation_Domain {
      text = '''The logical negation prefix operator `not` is defined for
                Booleans only, and returns a Boolean.'''
    }

    Static_Semantics Power_Semantics {
      text = '''The definition of exponentiation `**` is the usual one.'''
    }

    Static_Semantics Absolute_Value_Semantics {
      text = '''The definition of absolute value `abs` is the usual one.'''
    }

    Static_Semantics Negation_Semantics {
      text = '''The definition of logical negation `not` is the usual one.'''
    }

  }

}

section "Quantification" {

  Grammar Quantified_Expression {
    bnf = '''
      quantified_expression ::=
        '(' quantifier IDENTIFIER_name 'in' IDENTIFIER_component_name '=>'
        expression_PREDICATE ')'

      quantifier ::= 'forall' | 'exists'
    '''
  }

  Name_Resolution Quantification_Object {
    text = '''The component name must be defined in the current record,
              and must be an array type.'''
  }

  Static_Semantics Quantification_Naming_Scope {
    text = '''A quantified expression introduces a new name, that is valid
              only inside the predicate. This new name must
              not shadow any other. *(This means two
              separate quantified expressions may use the
              same name, but you may not nest and shadow,
              and you may not shadow a component name
              either.)*'''
  }

  Static_Semantics Quantification_Type {
    text = '''The type of the predicate must be Boolean. The result of a
              quantified expression is Boolean.'''
  }

  Dynamic_Semantics Universal_Quantification_Semantics {
    text = '''For universal *(forall)* quantification the final value is
              true iff all predicates evaluate to
              true. *(This means universal quantification
              over an empty array is vacuously true.)*'''
  }

  Dynamic_Semantics Existential_Quantification_Semantics {
    text = '''For existential *(exists)* quantification the final value is
              true iff the predicate evaluate to true at
              least once. *(This means existential
              quantification over an empty array is
              vacuously false.)*'''
  }

  Note Quantification_Evaluation {
    text = '''During evaluation of the quantified expression, each element
              of the array is evaluated in sequence and its
              value is bound to the declared name. The
              predicate is then evaluated with this
              binding.'''
  }

  Recommendation Quantification_Short_Circuit_Evaluation {
    text = '''In general Quantification is equivalent to a chain of `and`
              or `or` expressions, however it is left
              unspecified if quantification is using
              short-circuit semantics or not. It is
              recommended (for sanity) to do the following:'''
    bullets = ['''For actual evaluation, use short-circuit semantics, as speed
                  is important.''',
               '''For static analysis or linting, use non-short-circuit
                  semantics, as using a quantifier as a
                  complex guard is not reasonable.''']
    untraced_reason = "Non-normative text"
  }

}

section "Conditional expressions" {

  Grammar Conditional_Expression {
    bnf = '''
      conditional_expression ::=
      'if' expression_CONDITION 'then' expression_DEPENDENT
      {'elsif' expression_CONDITION 'then' expression_DEPENDENT }
      'else' expression_DEPENDENT
    '''
  }

  Static_Semantics Conditional_Expression_Types {
    text = '''The condition expressions must be of Boolean type. The
              dependent expressions must all be of the same
              type, and the type of the entire conditional
              expression is also of that type.'''
  }

  Dynamic_Semantics Conditional_Expression_Evaluation {
    text = '''Each condition is evaluated in sequence. Evaluation stops on
              the first condition that evaluates to true;
              after which the corresponding dependent
              expression is evaluated and returned.'''
  }

  Dynamic_Semantics Conditional_Expression_Else {
    text = '''If all conditions are evaluated to false, then the else
              dependent expression is evaluated and
              returned.'''
  }

}

section "TRLC Files" {

  Grammar TRLC_File {
    text = '''A `.trlc` file is simply a set of record object declarations.'''
    bnf = '''
      trlc_file ::= file_preamble
                    { trlc_entry }

      trlc_entry ::= section_declaration
                   | record_object_declaration
    '''
  }

  Static_Semantics Late_Package_Declarations {
    text = '''It is permitted to indicate a package that has
              not been declared in an `.rsl` file, in which
              case it is declared by the
              package_indication in the `.trlc` file. Such a package is
              declared late. If two `.trlc` files declare the same
              package, then it is unspecified which file actually
              declares it.'''
  }

  Note TRLC_Parse_Issue {
    text = '''For TRLC files it is impossible fully parse a file
              in isolation, since we must process at least the package
              indication of every other trlc file to know which import
              statements are valid.'''
  }

}

section "Sections" {

  Grammar Section_Declaration {
    text = '''A section has no semantic impact, and no impact on name
              resolution. Section names do not have to be
              unique. It may be exposed in an API, for
              example to section a HTML view of
              requirements.'''
    bnf = '''
      section_declaration ::= 'section' STRING_section_name
                              '{' { trlc_entry } '}'
    '''
  }

}

section "Record object declarations" {

  Grammar Record_Object_Declaration {
    bnf = '''
      record_object_declaration ::=
        qualified_name_RECORD_TYPE IDENTIFIER_object_name
        '{' { component_association } '}'

      component_association ::= IDENTIFIER_component_name '=' value

      value ::= [ adding_operator ] INTEGER
              | [ adding_operator ] DECIMAL
              | STRING
              | qualified_name_RECORD_OBJECT
              | qualified_name_ENUM_TYPE '.' IDENTIFIER_enumeration_literal
              | array_aggregate
              | tuple_aggregate

      array_aggregate ::= '[' [ value { ',' value } ] ']'

      tuple_aggregate ::= '(' value { ',' value } ')'
                        | value { separator_symbol value }
    '''
  }

  Static_Semantics Valid_Record_Types {
    text = '''The type of the declaration must be a valid, non-abstract
              record type. If no qualified name is given, the record type
              must be in the indicated package. *(Note that it is not
              legal to declare a tuple object.)*
           '''
  }

  Static_Semantics Unique_Object_Names {
    text = '''The name of the declaration must be a unique name and
              sufficiently distinct in the current
              package. *(See name resolution for a
              definition of sufficiently distinct.)* The
              name of the declaration must not shadow a type
              name or package.'''
  }

  Static_Semantics Valid_Components {
    text = '''Each component name must be a valid, non-frozen component
              of the record type. It is an error to attempt to assign to
              a frozen component *(even if the value assigned would be the
              same value as it's frozen value)*.'''
  }

  Static_Semantics Valid_Enumeration_Literals {
    text = '''Each enumeration must be a valid enumeration type in the
              indicated (or qualified) package. Each
              enumeration literal must be a valid literal of
              the indicated enumeration in the prefix.'''
  }

  Static_Semantics Matching_Value_Types {
    text = '''The type of each value must match each component or array
              element type. Records are specified through
              references *(there is no way to specify an
              inline anonymous instance)*.'''
  }

  Static_Semantics Mandatory_Components {
    text = '''It is an error to not provide a value for a non-optional
              component.'''
  }

  Static_Semantics Tuple_Syntax_Correct_Form {
    text = '''The aggregate of a tuple must use the correct form. A
              tuple without separators uses the bracket syntax
              (e.g. `(1, 2, 3)`, and a tuple with separators must
              use the separator syntax (e.g. `12345@42`).'''
  }

  Static_Semantics Tuple_Generic_Form {
    text = '''A tuple value for a tuple without separators must
              contain one value, in order, for each of its fields.'''
  }

  Static_Semantics Tuple_Separator_Form {
    text = '''A tuple value for a tuple with separators must
              contain the separator symbols as indicated in the type,
              in order. Optional fields and their preceding separator
              may be omitted. Once an optional field has been omitted,
              all following (optional) fields must also be omitted.'''
  }

  Dynamic_Semantics Evaluation_Of_Checks {
    text = '''A record object declaration creates a new binding for a
              record. The value of any frozen components is the value
              provided in the freezing declaration. After references
              are resolved, all applicable checks on the object, including
              any checks for tuples, are evaluated in the context
              of this binding.'''
  }

  Dynamic_Semantics Late_Reference_Checking {
    text = '''It is an error to refer to a record by name that does not
              exist. It is legal to refer to an record that
              has not been encountered yet, as references
              are resolved after parsing.'''
  }

  Dynamic_Semantics References_To_Extensions {
    text = '''A record reference must match in type, i.e. be of the
              correct type or any record extension of that
              type. *(For example if RE extends R, then a
              list of R may contain references to instances
              of R and RE. A list of RE may not contain any
              references to R.)*'''
  }

Dynamic_Semantics Single_Value_Assignment {
  text = '''A value can be assigned to a component of a record object
            only once.'''
}

  Note Tuple_Checks {
    text = '''The checks for a tuple aggregate are immediately evaluated
              after the last value is parsed.'''
  }

  Name_Resolution Sufficiently_Distinct {
    text = '''When declaring record objects there are wider rules that
              indicate name clashes. Specifically a record
              may not be declared if its "simplified name"
              clashes with any other "simplified name". A
              "simplified name" is the name converted to
              lowercase and all underscores removed.'''
  }

  Note Simplified_Name_Example {
    text = '''For example the simplified name of `Foo_Bar` is `foobar`
              and therefore it clashes with `Foobar`,
              `F_Oobar`, or `Foo_B_A_R`. But only at record
              declaration; when referring to other object
              you still have to use a precise match.'''
  }

  Note Simplified_Name_Rationale {
    text = '''The purpose of this rule is to avoid requirements that
              have hard to distinguish names.'''
  }

  Recommendation Record_Object_API {
    text = '''When exposing record instances through the API, it is
              required to make the type of the instance
              available. There are some alternatives,
              none of which are required:'''
    bullets = ['''Provide an implicit String record field named `type` that
                  carries this information (it is safe to do
                  that, as it is impossible to specify a
                  record type with a field named `type`).''',
               '''Provide a function or attribute that, when called, provides
                  the type information.''',
               '''Provide the type information through the type system of the
                  API language (e.g. the Python type system).''']
  }

  Example Record_Object_Examples {
    hidden_rsl = '''
      package Example
      tuple Codebeamer_Item {
        item Integer
        separator @
        version optional Integer
      }
      tuple Coordinate {
        x Decimal
        y Decimal
      }
      type Requirement {
        description String
        coordinate Coordinate
        derived_from_cb optional Codebeamer_Item [1 .. *]
      }
    '''
    hidden_trlc = '''package Example'''
    trlc = '''
      Requirement Potato {
        description = "Hello World!"
        coordinate = (42.0, 666.0)
        derived_from_cb = [
          1234,     // references codebeamer item 1234 (at head revision)
          1900@42   // references codebeamer item 1900 at version 42
        ]
      }
    '''
  }

}

section "Markup strings" {

  Text Markup_String_Format {
    text = '''A `Markup_String` allows you to inline references to TRLC
              record in a string. The format is limited and
              simple: any name or comma-separated list of
              names enclosed in double square brackets
              (i.e. `[[` and `]]`) is considered a
              reference.'''
  }

  Text Markup_String_Errors {
    text = '''Attempting to nest, or close a list that does not exist, or
              not close an open list before the end of the
              string is an error.'''
  }

  Static_Semantics Markup_String_Types {
    text = '''The fragment of BNF grammar applicable is
              qualified_name. The type of each named object
              must be a record type. *(This means you cannot
              reference types or enumerations.)*'''
  }

  Dynamic_Semantics Markup_String_Late_Reference_Resolution {
    text = '''The references are resolved late, just like an ordinary
              record reference. *(This means you can
              forward-reference objects, or reference
              yourself.)*'''
  }

  Name_Resolution Markup_String_Resolution {
    text = '''The name resolution rules for the qualified_name are exactly
              the same as they are for any other
              qualified_name. *(This means you need to
              import all packages from which you reference
              objects.)*'''
  }

  Example Markup_String_Examples {
    hidden_rsl = '''
      package Foo
      type Constant {
         value Integer
      }
      type Requirement {
         description Markup_String
      }
      enum License { GPL3 AGPL3 }
      type Tool {
         vendor String
         url String
         license License
      }
    '''
    hidden_trlc = '''package Foo'''
    trlc = '''
      Requirement Bean_Vehicle {
        description = "The car shall have [[WHEEL_COUNT]] wheels."
      }

      Requirement SW_Process {
        description = "We shall use [[TRLC, LOBSTER]] for achieving software traceability."
      }

      Constant WHEEL_COUNT {
        value = 3
      }

      Tool TRLC {
        vendor  = "BMW AG"
        url     = "https://github.com/bmw-software-engineering/trlc/"
        license = License.GPL3
      }

      Tool LOBSTER {
        vendor  = "BMW AG"
        url     = "https://github.com/bmw-software-engineering/lobster/"
        license = License.AGPL3
      }
    '''
  }

}

section "Null Values" {

  Static_Semantics Restricted_Null {
    text = '''The literal null value is only permitted to appear in
              an equality or inequality. Any other context (such as
              `(if a then null else b)` is rejected statically.'''
  }

  Static_Semantics Null_Equivalence {
    text = '''The expression `null == null` is statically true.'''
  }

  Dynamic_Semantics Unspecified_Optional_Components {
    text = '''The value of an optional component or field that is
              not specified is `null`.'''
  }

  Dynamic_Semantics Null_Is_Invalid {
    text = '''For any other operator or operation, the null value is
              considered out of bounds and raises an
              error. *(This means you can check if something
              is null or not, but any other use will cause
              an error.)*'''
  }
}  

section "Acyclic Dependency" {

  Static_Semantics Acyclic_Record_Extensions {
    text = '''A record type shall not extend itself or another record 
              type that extends it.''' 
  }

  Note Acyclic_Record_Graph {
    text = '''A record may only extend a different record type that
              does not eventually lead back to it. A record referring 
              to itself directly or indirectly creates ambiguities.'''
  } 
 
}

section "Forward declarations in '.rsl' file" {

  Static_Semantics Forward_Declaration_Record_Types {
    text = '''It is allowed for a record type to refer to a record type
              declared later in the same `.rsl` file, regardless of the
              order in which types are declared.'''              
  }

  Static_Semantics Forward_Declaration_Tuple_Types {
    text = '''It is allowed for a tuple field to refer to a record type
              declared later in the same `.rsl` file, regardless of the
              order in which types are declared.'''
  }

  Static_Semantics Forward_Declaration_Union_Types {
    text = '''It is allowed for a union type to refer to a record type
              declared later in the same `.rsl` file, regardless of the
              order in which types are declared.'''
  }  

  Static_Semantics Forward_Declaration_Checks {
    text = '''The `check` statement in an `.rsl` file cannot refer to a 
              record type declared later in the same `.rsl` file.'''
  }

  Recommendation Forward_Declaration_Resolution_Order {
    text = '''It is recommended to resolve the forward references in an
              implementation. If the referenced type cannot be found, 
              the implementation shall report a static error instead of 
              accepting an unresolved or recursive reference.'''
  }

  Recommendation Forward_Reference_Resolution {
    text = '''It is recommended that the implementation must resolve every
              referenced name that is declared later in the same '.rsl' 
              file before a type, record object, or check is accepted in 
              '.rsl' file. The implementation shall report a static error 
              if any required declaration cannot be found.'''
  }

}
